--  **********************************************************
-- Airespace Wireless MIB
-- Copyright 2005 Cisco Systems, Inc.  All rights reserved.

-- This SNMP Management Information Specification
-- embodies Cisco's confidential and proprietary
-- intellectual property.  Cisco retains all title
-- and ownership in the Specification including any revisions.

-- This Specification is supplied "AS IS", Cisco
-- makes no warranty, either expressed or implied,
-- as to the use, operation, condition, or performance of the
-- Specification.


-- Status: Release
-- Version: 4.0
-- Internal Source Code Version:1.268
-- Date: 01 Jan 2006
--  **********************************************************

AIRESPACE-WIRELESS-MIB DEFINITIONS ::= BEGIN
    IMPORTS
        MODULE-IDENTITY,
        OBJECT-TYPE,
        NOTIFICATION-TYPE,
        Integer32,
        Counter32,
        Unsigned32,
        Counter64,
        Gauge32,
        IpAddress,
        TimeTicks
    FROM SNMPv2-SMI
        NOTIFICATION-GROUP, 
        OBJECT-GROUP,
        MODULE-COMPLIANCE
    FROM SNMPv2-CONF
        TEXTUAL-CONVENTION,
        DisplayString,
        RowStatus,
        MacAddress,
        TruthValue,
        TimeInterval
    FROM SNMPv2-TC
        airespace
    FROM AIRESPACE-REF-MIB;

--********************************************************************
--*  MODULE IDENTITY
--********************************************************************

    bsnWireless MODULE-IDENTITY
        LAST-UPDATED "200604100000Z"
        ORGANIZATION "Airespace, Inc."
        CONTACT-INFO
            "        Cisco Systems,
                     Customer Service
             Postal: 170 West Tasman Drive
                     San Jose, CA  95134
                     USA
                Tel: +1 800 553-NETS

              Email: cs-wnbu-snmp@cisco.com"
        DESCRIPTION
                "This MIB is intended to be implemented on all those
                devices operating as Central Controllers (CC) that
                terminate the Light Weight Access Point Protocol
                tunnel from Light-weight LWAPP Access Points.

                This MIB provides configuration and status information
                for 802.11 Access Points, LAN configuration, AAA,
                Mobility, IpSec, Radio Rescouce Management and 802.11 
                global parameters.  

                The relationship between controller and the LWAPP 
                APs can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.
               
                                   GLOSSARY
 
                Access Point ( AP )

                An entity that contains an 802.11 medium access
                control ( MAC ) and physical layer ( PHY ) interface
                and provides access to the distribution services via
                the wireless medium for associated clients.  

                LWAPP APs encapsulate all the 802.11 frames in
                LWAPP frames and sends it to the controller to which
                it is logically connected.

                Basic Service Set Identifier (BSSID)

                The identifier for the service set comprising of
                all the 802.11 stations under the control of
                one coordinating Access Point.  This identifier
                happens to be the MAC address of the dot11 radio
                interface of the Access Point.  The wireless
                clients that associate with the Access Point
                get the wired uplink through this particular 
                dot11 interface. 

                Central Controller ( CC )

                The central entity that terminates the LWAPP protocol
                tunnel from the LWAPP APs.  Throughout this MIB,
                this entity also referred to as 'controller'. 

                Light Weight Access Point Protocol ( LWAPP ) 

                This is a generic protocol that defines the 
                communication between the Access Points and the
                Central Controller. 

                Mobile Node ( MN )

                A roaming 802.11 wireless device in a wireless
                network associated with an access point. 

                Station Management (SMT)

                This term refers to the internal management of the
                802.11 protocol operations by the AP to work
                cooperatively with the other APs and 802.11
                devices in the network.
 
                REFERENCE
 
                [1] Part 11 Wireless LAN Medium Access Control ( MAC )
                and Physical Layer ( PHY ) Specifications.
  
                [2] Draft-obara-capwap-lwapp-00.txt, IETF Light 
                Weight Access Point Protocol. "
        
        REVISION    "200604100000Z"

        DESCRIPTION
                   "Updated MIB with description and format"

        REVISION    "200510300000Z"

        DESCRIPTION
                   "Airespace MIB"
 
        ::= { airespace 2 }

-- *******************************************************************
-- *  Major sections
-- *******************************************************************


--  Airespace Wireless LAN Configuration Attributes
--  DEFINED AS "The bsnEss object provides all the
--  configuration and operation of Wireless LAN";

    bsnEss OBJECT IDENTIFIER ::= { bsnWireless 1}

--  Airespace AP Attributes
--  DEFINED AS "The bsnAP object provides all the
--  configuration and operation of Airespace APs that
--  are associated with the Switch";

    bsnAP OBJECT IDENTIFIER ::= { bsnWireless 2}

-- Airespace 802.11 Standard Attributes applied Globally
-- DEFINED AS "The bsnGlobalDot11 object class provides support for
-- standard 802.11 parameters for STM,MAC,RES,PHY which would be common
-- to all WLAN on Airespace"

    bsnGlobalDot11 OBJECT IDENTIFIER ::= { bsnWireless 3}

--  Airespace Radio Resource Management Configuration Parameters
--  DEFINED AS "The bsnRrm object provides all the
--  configuration and monitoring of RF Group parameters ";

    bsnRrm OBJECT IDENTIFIER ::= { bsnWireless 4}

--  Airespace Authentication, Authorization, and Accounting Attributes
--  DEFINED AS "The bsnAaa object class provides all standard
--  information to support configuration of RADIUS and TACACS+
--  client operation.";

    bsnAAA OBJECT IDENTIFIER ::= {bsnWireless 5}


-- Airespace Trap Configuration and Trap definition
-- DEFINED AS "The bsnTrap object class provides all notification that
-- Switch need to generate for Management System. It also provides to
-- configure generation of notification.

    bsnTrap OBJECT IDENTIFIER ::= { bsnWireless 6 }

-- Airespace General Utilities
-- DEFINED AS "The bsnUtility object class provides utilities like
-- Ping, LinkTest, Syslog that are supported by the Switch

    bsnUtility OBJECT IDENTIFIER ::= { bsnWireless 7 }

-- Airespace Mobility Group Parameters
-- DEFINED AS "The bsnMobility object class provides configuration
-- of Mobility Group and Mobility Statistics.

    bsnMobility OBJECT IDENTIFIER ::= { bsnWireless 8 }

-- Airespace Global IpSec Group
-- DEFINED AS "The bsnIpsec object class provides configuration
-- of ID and CA Certificates

    bsnIpsec  OBJECT IDENTIFIER ::= { bsnWireless 9 }

    bsnWrasGroups            OBJECT IDENTIFIER ::= { bsnWireless 50 }
    bsnWrasCompliances       OBJECT IDENTIFIER ::= { bsnWireless 51 }


-- *******************************************************************
-- *  Textual conventions from BSN MIB definitions
-- *******************************************************************
    WEPKeytype ::= OCTET STRING (SIZE (4..32))
    ProfileState ::= INTEGER { pass (1), fail (0) }

BsnTxtSignatureMacInfo ::= TEXTUAL-CONVENTION
        STATUS     current
        DESCRIPTION
                "This textual convention defines the pattern followed
                by the LWAPP APs to perform signature analysis with
                the signature and report the results to the
                Controller.
        
                The semantics are described as follows.
        
                bsnSignatureMacAll - The Controller would set the
                'Mac Info' parameter of the 'Signature Add LWAPP
                Message' to this value to indicate the LWAPP AP that
                the signature analysis and pattern matching should
                be tracked and reported on a per-signature and
                per-channel basis.
         
                bsnSignatureMacIndividual - The Controller would set
                the 'Mac Info' parameter of the 'Signature Add LWAPP
                Message' to this value to indicate the LWAPP AP that
                the signature analysis and pattern matching should
                be tracked and reported separately for individual
                MAC addresses, that are the sources of the received
                802.11 data and/or management frames.

                bsnStandardSigMacBoth - The Controller would set the
                'Mac Info' parameter of the 'Signature Add LWAPP
                Message' to this value to indicate the LWAPP AP that
                the signature analysis and pattern matching should
                be tracked on a per signature as well as per-MAC
                address basis. "
        SYNTAX  INTEGER {
                        bsnSignatureMacAll(0),
                        bsnSignatureMacIndividual(1),
                        bsnSignatureMacBoth(2)
        }


BsnSignaturePatternOffSetStart ::= TEXTUAL-CONVENTION
        STATUS     current
        DESCRIPTION
                "This object indicates how an offset should be applied
                while doing signature analysis for QOS and non-QOS
                data frames.  This is introduced since 802.11e QOS
                frames have an additional 2-byte QOS header which
                results in the current implementation not being
                able to find the start of the date frames for
                signature analysis.  The semantics of the values are
                as follows.

                sigPattStartFrm - This indicates that the
                required offset should be applied to the start of
                the data frame, before performing pattern matching
                of the signature on the data frame.

                sigPattStartFrmBody - This value indicates
                that the required offset should be applied to the
                start of the frame body, after the header, before
                performing pattern matching of the signature on the
                data frame. "
        SYNTAX     INTEGER {
                           sigPattStartFrm(0),
                           sigPattStartFrmBody(1)
                   }

-- ************************************************************
-- *  MIB attribute OBJECT-TYPE definitions follow
-- ************************************************************


-- ***********************************************************
-- *  bsnEss Objects
-- * Airespace IEEE 802.11 Extended Service Set Table
-- *
-- ***********************************************************

bsnDot11EssTable OBJECT-TYPE
    SYNTAX SEQUENCE OF BsnDot11EssEntry
    MAX-ACCESS not-accessible
    STATUS current
    DESCRIPTION
        "Ess(WLAN) Configuration Table indexed by bsnDot11EssIndex.
         Maximum of 17 WLANs can be created on Airespace Switch. 
         bsnDot11EssIndex of 17 is reserved for WLAN for Third Party 
         APs(non-Airespace APs)."
    ::= { bsnEss 1 }

bsnDot11EssEntry OBJECT-TYPE
    SYNTAX BsnDot11EssEntry
    MAX-ACCESS not-accessible
    STATUS current
    DESCRIPTION
        "An entry in bsnDot11EssTable"
    INDEX { bsnDot11EssIndex }
    ::= { bsnDot11EssTable 1 }

BsnDot11EssEntry ::=
    SEQUENCE {
        bsnDot11EssIndex                    Unsigned32,
        bsnDot11EssSsid                     DisplayString,
        bsnDot11EssSessionTimeout           Unsigned32,
        bsnDot11EssMacFiltering             INTEGER,
        bsnDot11EssAdminStatus              INTEGER,
        bsnDot11EssSecurityAuthType         INTEGER,
        bsnDot11EssStaticWEPSecurity        INTEGER,
        bsnDot11EssStaticWEPEncryptionType  INTEGER,
        bsnDot11EssStaticWEPDefaultKey      WEPKeytype,
        bsnDot11EssStaticWEPKeyIndex        INTEGER,
        bsnDot11EssStaticWEPKeyFormat       INTEGER,
        bsnDot11Ess8021xSecurity            INTEGER,
        bsnDot11Ess8021xEncryptionType      INTEGER,
        bsnDot11EssWPASecurity              INTEGER,
        bsnDot11EssWPAEncryptionType        INTEGER,
        bsnDot11EssWPAAuthKeyMgmtMode       INTEGER,
        bsnDot11EssWPAAuthPresharedKey      OCTET STRING,
        bsnDot11EssWPAAuthPresharedKeyHex   OCTET STRING,
        bsnDot11EssIpsecSecurity            INTEGER,
        bsnDot11EssVpnEncrTransform         INTEGER,
        bsnDot11EssVpnAuthTransform         INTEGER,
        bsnDot11EssVpnIkeAuthMode           INTEGER,
        bsnDot11EssVpnSharedKey             OCTET STRING,
        bsnDot11EssVpnSharedKeySize         Unsigned32,
        bsnDot11EssVpnIkePhase1Mode         INTEGER,
        bsnDot11EssVpnIkeLifetime           Integer32,
        bsnDot11EssVpnIkeDHGroup            INTEGER,
        bsnDot11EssIpsecPassthruSecurity    INTEGER,
        bsnDot11EssVpnPassthruGateway       IpAddress,
        bsnDot11EssWebSecurity              INTEGER,
        bsnDot11EssRadioPolicy              INTEGER,
        bsnDot11EssQualityOfService         INTEGER,
        bsnDot11EssDhcpRequired             INTEGER,
        bsnDot11EssDhcpServerIpAddress      IpAddress,
        bsnDot11EssVpnContivityMode         INTEGER,
        bsnDot11EssVpnQotdServerAddress     IpAddress,
        bsnDot11EssBlacklistTimeout         Integer32,
        bsnDot11EssNumberOfMobileStations   Counter32,
        bsnDot11EssWebPassthru              INTEGER,
        bsnDot11EssCraniteSecurity          INTEGER,
        bsnDot11EssBlacklistingCapability   INTEGER,
        bsnDot11EssInterfaceName            DisplayString,
        bsnDot11EssAclName                  DisplayString,
        bsnDot11EssAAAOverride              INTEGER,
        bsnDot11EssWepAllowSharedKeyAuth    INTEGER,
        bsnDot11EssFortressSecurity         INTEGER,
        bsnDot11EssL2tpSecurity             INTEGER,
        bsnDot11EssBroadcastSsid            INTEGER,
        bsnDot11EssExternalPolicyValidation INTEGER,
        bsnDot11EssRSNSecurity              INTEGER,
        bsnDot11EssRSNWPACompatibilityMode  INTEGER,
        bsnDot11EssRSNAllowTKIPClients      INTEGER,
        bsnDot11EssRSNAuthKeyMgmtMode       INTEGER,
        bsnDot11EssRSNAuthPresharedKey      OCTET STRING,
        bsnDot11EssRSNAuthPresharedKeyHex   OCTET STRING,
        bsnDot11EssIPv6Bridging             INTEGER,
        bsnDot11EssRowStatus                RowStatus,
        bsnDot11EssWebPassthroughEmail      INTEGER,
        bsnDot11EssWmePolicySetting         INTEGER,
        bsnDot11Ess80211ePolicySetting      INTEGER,
        bsnDot11EssRadiusAuthPrimaryServer   DisplayString,
        bsnDot11EssRadiusAuthSecondaryServer DisplayString,
        bsnDot11EssRadiusAuthTertiaryServer  DisplayString,
        bsnDot11EssRadiusAcctPrimaryServer   DisplayString,
        bsnDot11EssRadiusAcctSecondaryServer DisplayString,
        bsnDot11Ess7920PhoneSupport          INTEGER,      
        bsnDot11EssRadiusAcctTertiaryServer  DisplayString
    }

bsnDot11EssIndex OBJECT-TYPE
        SYNTAX Unsigned32 (1..17)
        MAX-ACCESS read-create
        STATUS current
        DESCRIPTION
           "Index of the Ess(WLAN) within Airespace Switch.
            Airespace Switch supports 17 ESS(Wlans) so index
            will be from 1 to 17. 17 is to be used for ESS(WLAN)
            created for support of Third Party APs(non-Airespace APs)"
    ::= { bsnDot11EssEntry 1 }

bsnDot11EssSsid OBJECT-TYPE
        SYNTAX DisplayString (SIZE(1..32))
        MAX-ACCESS read-create
        STATUS current
        DESCRIPTION
             "SSID assigned to ESS(WLAN)"
    ::= { bsnDot11EssEntry 2 }

bsnDot11EssSessionTimeout OBJECT-TYPE
        SYNTAX Unsigned32 (0..86400)
        MAX-ACCESS read-create
        STATUS current
        DESCRIPTION
                "Maximum time of a Mobile Station session.
                 Value of 0 means infinite time(no timeout set)."
        DEFVAL { 0 }
    ::= { bsnDot11EssEntry 4 }

bsnDot11EssMacFiltering OBJECT-TYPE
        SYNTAX INTEGER { disable (0), enable (1)}
        MAX-ACCESS read-create
        STATUS current
        DESCRIPTION
                 "A type of security policy for Mobile Stations 
                  (Clients). Select to filter clients by MAC address. 
                  By selecting this Security, you need to create 
                  MacFilters in bsnUsersTable or have MacFilters 
                  configured on Radius Servers specified in 
                  bsnRadiusAuthenticationTable"
        DEFVAL { disable }
    ::= { bsnDot11EssEntry 5 }

bsnDot11EssAdminStatus OBJECT-TYPE
        SYNTAX INTEGER { disable (0), enable (1)}
        MAX-ACCESS read-create
        STATUS current
        DESCRIPTION
                "Administrative Status of ESS(WLAN). By disabling an 
                 ESS the corresponding SSID is no longer broadcasted 
                 in AP beacons."
        DEFVAL { disable }
    ::= { bsnDot11EssEntry 6 }

bsnDot11EssSecurityAuthType OBJECT-TYPE
        SYNTAX INTEGER { authOpen (0),
                         authSharedKey(1),
                         authCiscoLeap (128)}
                MAX-ACCESS read-only
                STATUS current
        DESCRIPTION
                "Type of 802.11 Authentication."
        DEFVAL { authOpen }
    ::= { bsnDot11EssEntry 7 }

bsnDot11EssStaticWEPSecurity OBJECT-TYPE
       SYNTAX INTEGER { enable (1),disable (0)}
       MAX-ACCESS read-create
       STATUS current
       DESCRIPTION
       "Status of Static WEP Security policy. If enabled, WEP 
        Encryption WEP Default Key, Key Index and Key Format should 
        also be specified."
       DEFVAL { disable }
       ::= { bsnDot11EssEntry 8 }

bsnDot11EssStaticWEPEncryptionType OBJECT-TYPE
        SYNTAX INTEGER {
                        wep104 (0),
                        wep40 (2),
                        wep128 (3)
                        }
        MAX-ACCESS read-create
        STATUS current
        DESCRIPTION
            "Type of Static WEP Encryption. Length of key specified in
             Default Key depends on this attribute."
        DEFVAL { wep104 }
    ::= { bsnDot11EssEntry 9 }

bsnDot11EssStaticWEPDefaultKey OBJECT-TYPE
        SYNTAX WEPKeytype
        MAX-ACCESS read-create
        STATUS current
        DESCRIPTION
                "Static WEP Default Key. For wep104 encryption either 
                 26 bit hex key or 13 bit ascii key should be 
                 specified.  For wep40 encryption 10 bit hex key or 5 
                 bit ascii key should be specified. For wep128
                 encryption 32 bit hex key or 16 bit ascii key should 
                 be specified."
    ::= { bsnDot11EssEntry 10 }

bsnDot11EssStaticWEPKeyIndex OBJECT-TYPE
        SYNTAX INTEGER(0..4)
        MAX-ACCESS read-create
        STATUS current
        DESCRIPTION
                "According to 802.11 standard 4 keys are supported.
                 So 802.11 Mobile Stations(Client) can have upto 4 
                 keys.  This index is for informing Mobile Station 
                 which key it should use for Static WEP Authentication"
    ::= { bsnDot11EssEntry 11 }

bsnDot11EssStaticWEPKeyFormat OBJECT-TYPE
        SYNTAX INTEGER {hex(1),ascii(2),default(0)}
        MAX-ACCESS read-create
        STATUS current
        DESCRIPTION
                "This is not persistant.Reading this attribute will
                always return default. The format of the key specified
                in Airespace switch keeps record of the Index."
    ::= { bsnDot11EssEntry 12 }

bsnDot11Ess8021xSecurity OBJECT-TYPE
        SYNTAX INTEGER { enable (1),disable (0)}
        MAX-ACCESS read-create
        STATUS current
        DESCRIPTION
                "Status of 802.1X security policy."
        DEFVAL { enable }
        ::= { bsnDot11EssEntry 13 }

bsnDot11Ess8021xEncryptionType OBJECT-TYPE
        SYNTAX INTEGER {
                        wep104 (0),
                        wep40 (2),
                        wep128 (3)
                        }
        MAX-ACCESS read-create
        STATUS current
        DESCRIPTION
                "Type of 802.1X Encryption. This applies if 
                 bsnDot11Ess8021xSecurity is in enabled state."
        DEFVAL { wep104 }
    ::= { bsnDot11EssEntry 14 }

bsnDot11EssWPASecurity OBJECT-TYPE
        SYNTAX INTEGER { enable (1),disable (0)}
        MAX-ACCESS read-create
        STATUS deprecated
        DESCRIPTION
                "Status of WPA security policy.
                 This has been deprecated for cLWSecDot11EssCckmTable."
        DEFVAL { disable }
        ::= { bsnDot11EssEntry 16 }

bsnDot11EssWPAEncryptionType OBJECT-TYPE
        SYNTAX INTEGER {
                        wep104 (0),
                        wep40 (2),
                        wep128 (3),
                        tkipmic (5)
                        }
        MAX-ACCESS read-create
        STATUS deprecated
        DESCRIPTION
                "Type of WPA Encryption. This applies when 
                 bsnDot11EssWPASecurity is in enable state.
                 This has been deprecated for cLWSecDot11EssCckmTable."
        DEFVAL { tkipmic }
    ::= { bsnDot11EssEntry 17 }

bsnDot11EssIpsecSecurity OBJECT-TYPE
        SYNTAX INTEGER { enable (1),disable (0)}
        MAX-ACCESS read-create
        STATUS current
        DESCRIPTION
            "Status of IpSec (VPN) security policy. Note that this 
             cannot be applied with Web security policy."
        DEFVAL { disable }
        ::= { bsnDot11EssEntry 18 }

bsnDot11EssVpnEncrTransform OBJECT-TYPE
        SYNTAX INTEGER { tripleDes (0),
                         none (1),
                         des (2),
                         aesCbc (3)
                         }
        MAX-ACCESS read-create
        STATUS current
        DESCRIPTION
                "The Encryption algorithm employed by this Vpn(IpSec) 
                 Encryption.  This applies only when 
                 bsnDot11EssIpsecSecurity is in enable state."
        DEFVAL { tripleDes }
    ::= { bsnDot11EssEntry 19 }

bsnDot11EssVpnAuthTransform OBJECT-TYPE
        SYNTAX INTEGER { none (1), hmacMd5 (2), hmacSha1 (0)}
                MAX-ACCESS read-create
        STATUS current
        DESCRIPTION
                "The Hash algorithm employed by the Vpn Encrpytion.
                 This applies only when bsnDot11EssIpsecSecurity is in 
                 enable state."
        DEFVAL { hmacSha1 }
    ::= { bsnDot11EssEntry 20 }

bsnDot11EssVpnIkeAuthMode OBJECT-TYPE
        SYNTAX INTEGER { xauthEnablePsk(0),
            certificate (2), presharedKey (3)}
                MAX-ACCESS read-create
        STATUS current
        DESCRIPTION
                "The authentication type of the SA. It could be a 
                 certificate or a pre-shared key or xauthEnablePsk.
                 This applies only when bsnDot11EssIpsecSecurity is 
                 in enable state."
        DEFVAL { presharedKey }
    ::= { bsnDot11EssEntry 21 }

bsnDot11EssVpnSharedKey OBJECT-TYPE
        SYNTAX OCTET STRING (SIZE(1..128))
                MAX-ACCESS read-create
        STATUS current
        DESCRIPTION
                "VPN Shared Key. This applies only when 
                 bsnDot11EssVpnSharedKey is in enable state and 
                 bsnDot11EssVpnIkeAuthMode is xauthEnablePsk or 
                 presharedKey."
    ::= { bsnDot11EssEntry 22 }

bsnDot11EssVpnSharedKeySize OBJECT-TYPE
        SYNTAX Unsigned32(0..128)
                MAX-ACCESS read-only
        STATUS current
        DESCRIPTION
                "VPN Shared Key size. This applies only when 
                 bsnDot11EssVpnSharedKey is in enable state
                 and bsnDot11EssVpnIkeAuthMode is xauthEnablePsk or 
                 presharedKey."
    ::= { bsnDot11EssEntry 23 }

bsnDot11EssVpnIkePhase1Mode OBJECT-TYPE
        SYNTAX INTEGER { agressive (0), main (1)}
                MAX-ACCESS read-create
        STATUS current
        DESCRIPTION
                "VPN IKE Phase 1 Mode type as per the IpSec standards.
                This applies only when bsnDot11EssIpsecSecurity is in 
                enable state."
        DEFVAL {main}
    ::= { bsnDot11EssEntry 24 }

bsnDot11EssVpnIkeLifetime OBJECT-TYPE
        SYNTAX Integer32 (1800..345600)
                MAX-ACCESS read-create
        STATUS current
        DESCRIPTION
                "Vpn IKE's Lifetime.
                 This applies only when bsnDot11EssIpsecSecurity is in
                 enable state."
        DEFVAL {57600}
    ::= { bsnDot11EssEntry 25 }

bsnDot11EssVpnIkeDHGroup OBJECT-TYPE
        SYNTAX INTEGER { group2(0), group1(1), group5(4)}
                MAX-ACCESS read-create
        STATUS current
        DESCRIPTION
                "IKE's Diffie-Hellman Group.
                 This applies only when bsnDot11EssIpsecSecurity is in 
                 enable state."
        DEFVAL {group2}
    ::= { bsnDot11EssEntry 26 }

bsnDot11EssIpsecPassthruSecurity OBJECT-TYPE
        SYNTAX INTEGER { enable (1),disable (0)}
        MAX-ACCESS read-create
        STATUS current
        DESCRIPTION
                "Status of IpSec Passthru security policy."
        DEFVAL { disable }
        ::= { bsnDot11EssEntry 27 }

bsnDot11EssVpnPassthruGateway OBJECT-TYPE
        SYNTAX IpAddress
        MAX-ACCESS read-create
        STATUS current
        DESCRIPTION
             "Ip address of VpnPassthru Gateway.
              This applies only when bsnDot11EssIpsecPassthruSecurity 
              is in enable state."
        DEFVAL { '00000000'H }
    ::= { bsnDot11EssEntry 28 }

bsnDot11EssWebSecurity OBJECT-TYPE
        SYNTAX INTEGER { enable (1),disable (0)}
        MAX-ACCESS read-create
        STATUS current
        DESCRIPTION
            "Status of Web security policy. Note this policy cannot be 
             applied with IpSec security policy."
        DEFVAL { disable }
        ::= { bsnDot11EssEntry 29 }

bsnDot11EssRadioPolicy OBJECT-TYPE
        SYNTAX INTEGER { all(0),dot11aOnly(2),dot11bOnly(1),
                        dot11gOnly(3),dot11bgOnly(4),
                        dot11agOnly(5),dot11abOnly(6)}
        MAX-ACCESS read-create
        STATUS current
        DESCRIPTION
        "Radio Policy for a WLAN. It can either be All where it
         will be applicable to ALL types of protocols or it can be
         set to apply to combinations of 802.11a, 802.11b, 802.11g."
        DEFVAL { all }
        ::= { bsnDot11EssEntry 30 }

bsnDot11EssQualityOfService OBJECT-TYPE
        SYNTAX INTEGER { bronze (0),silver (1),gold(2), platinum(3)}
        MAX-ACCESS read-create
        STATUS current
        DESCRIPTION
        "Quality of Service for a WLAN.Services such as VoIP should 
         be set to Gold while non-discriminating services such as 
         messaging can be set to Bronze."
        DEFVAL { bronze }
        ::= { bsnDot11EssEntry 31 }

bsnDot11EssDhcpRequired OBJECT-TYPE
    SYNTAX INTEGER { disable (0), enable (1) }
    MAX-ACCESS read-create
    STATUS current
    DESCRIPTION
        "DHCP required for all clients on this WLAN"
    DEFVAL { disable }
    ::= {  bsnDot11EssEntry 32 }

bsnDot11EssDhcpServerIpAddress OBJECT-TYPE
        SYNTAX IpAddress
        MAX-ACCESS read-create
        STATUS current
        DESCRIPTION
            "IP Address of the DHCP Server. Make it 0.0.0.0 to disable
             DHCP Relay. Any value other than 0.0.0.0, it will be 
             assumed that DHCP Relay is turned on."
        DEFVAL { '00000000'H }
        ::= { bsnDot11EssEntry 33 }

bsnDot11EssVpnContivityMode OBJECT-TYPE
    SYNTAX INTEGER { disable (0), enable (1) }
    MAX-ACCESS read-create
    STATUS current
    DESCRIPTION
        "Specifies if contivity mode for the IpSec is enabled.
         If enabled, user needs to specify the Quote of the Day 
         Server's IPAddress in bsnDot11EssVpnQotdServerAddress."
    DEFVAL { disable }
    ::= {  bsnDot11EssEntry 34 }

bsnDot11EssVpnQotdServerAddress OBJECT-TYPE
        SYNTAX IpAddress
        MAX-ACCESS read-create
        STATUS current
        DESCRIPTION
            "IP Address of the Quote of the Day Server."
        DEFVAL { '00000000'H }
        ::= { bsnDot11EssEntry 35 }
        
bsnDot11EssBlacklistTimeout OBJECT-TYPE
        SYNTAX Integer32 (0..2147483647)
        MAX-ACCESS read-create
        STATUS current
        DESCRIPTION
            "Set the timeout for blacklisted Mobile Stations after 
             which the mobile station will be automatically 
             de-authenticated. Mobile Station are blacklisted by MAC 
             address and their status can be obtained from 
             bsnMobileStationStatus.
             A timeout setting of 0 indicates no blacklist timeout is 
             set and administrative control 
             (bsnMobileStationDeleteAction ) is required to 
             deauthenticate the station."
        DEFVAL { 60 }
        ::= { bsnDot11EssEntry 37 }

bsnDot11EssNumberOfMobileStations OBJECT-TYPE
        SYNTAX Counter32
        MAX-ACCESS read-only
        STATUS current
        DESCRIPTION
                "No of Mobile Stations currently associated with the 
                 WLAN."
        ::= { bsnDot11EssEntry 38 }

bsnDot11EssWebPassthru OBJECT-TYPE
        SYNTAX INTEGER { enable (1),disable (0)}
        MAX-ACCESS read-create
        STATUS current
        DESCRIPTION
            "For switches with version before 2.0: This is applicable 
             only when the Web Security Type is enabled. When this 
             attribute is enabled, it allows a client's NetBIOS packets
             to go through the switch before web auth is completed.

             (This is obsolete for Switch versions 2.0 to 2.2).

             For switch verions 3.0 and above: This is reintroduced as 
             the web policy where the client is connected
             through the web without authentication that is there is no
             username/password input required.  Moreover, if the 
             bsnDot11EssWebPassthroughEmail is enabled, the user will 
             be asked to enter an email address."
        DEFVAL { disable }
        ::= { bsnDot11EssEntry 39 }

bsnDot11EssCraniteSecurity OBJECT-TYPE
       SYNTAX INTEGER { enable (1),disable (0)}
       MAX-ACCESS read-create
       STATUS current
       DESCRIPTION
            "Status of Cranite Passthrough Security policy. If enabled,
             no other security can be enabled."
       DEFVAL { disable }
       ::= { bsnDot11EssEntry 40 }

bsnDot11EssBlacklistingCapability OBJECT-TYPE
        SYNTAX INTEGER { disable (0), enable (1)}
        MAX-ACCESS read-create
        STATUS current
        DESCRIPTION
                 "This is the flag that can enable or disable the 
                  client backlisting feature for a WLAN. If enabled, 
                  the clients can be blacklisted by the Switch in case
                  of repetitive auth failure and other reasons like it.
                  If disabled, the clients cannot be blacklisted by 
                  the switch. The blacklist timeout value will only 
                  be effective if this feature is turned on."
        DEFVAL { disable }
    ::= { bsnDot11EssEntry 41 }

bsnDot11EssInterfaceName OBJECT-TYPE
        SYNTAX DisplayString (SIZE(1..32))
        MAX-ACCESS read-create
        STATUS current
        DESCRIPTION
             "Name of the interface used by this WLAN. By default it 
              is set to be the management interface."
    ::= { bsnDot11EssEntry 42 }

bsnDot11EssAclName OBJECT-TYPE
        SYNTAX DisplayString (SIZE(0..32))
        MAX-ACCESS read-create
        STATUS current
        DESCRIPTION
             "Name of ACL for the WLAN. This is applicable only when 
              Web Authentication is enabled as a security.
              An empty string value indicates that no ACL has been 
              set (which is a valid option)"
    ::= { bsnDot11EssEntry 43 }

bsnDot11EssAAAOverride OBJECT-TYPE
    SYNTAX INTEGER { disable (0), enable (1) }
    MAX-ACCESS read-create
    STATUS current
    DESCRIPTION
         "Enable or Disable AAA override for the global WLAN 
          parameters."
    DEFVAL { disable }
    ::= {  bsnDot11EssEntry 44 }

bsnDot11EssWPAAuthKeyMgmtMode OBJECT-TYPE
    SYNTAX INTEGER { disable (0), enable (1) }
    MAX-ACCESS read-create
    STATUS deprecated
    DESCRIPTION
        "Enable or Disable WPA Pre-shared Key Mode. If enabled, a 
         preshared key should be set for WPA authentication.
         This has been deprecated for cLWSecDot11EssCckmTable."
    DEFVAL { disable }
    ::= {  bsnDot11EssEntry 45 }

bsnDot11EssWPAAuthPresharedKey OBJECT-TYPE
        SYNTAX OCTET STRING (SIZE(8..63))
                MAX-ACCESS read-create
        STATUS deprecated
        DESCRIPTION
               "WPA Authentication Preshared Key. This applies only 
                when bsnDot11EssWPAAuthKeyMgmtMode is in enable state.
                This has been deprecated for cLWSecDot11EssCckmTable."
    ::= { bsnDot11EssEntry 46 }

bsnDot11EssWepAllowSharedKeyAuth OBJECT-TYPE
       SYNTAX INTEGER { enable (1),disable (0)}
       MAX-ACCESS read-create
       STATUS current
       DESCRIPTION
            "Enable this flag to allow Shared Key Authentication when 
             Static WEP is enabled."
       DEFVAL { disable }
       ::= { bsnDot11EssEntry 48 }


bsnDot11EssFortressSecurity OBJECT-TYPE
       SYNTAX INTEGER { enable (1),disable (0)}
       MAX-ACCESS read-create
       STATUS current
       DESCRIPTION
            "Status of Fortress Passthrough Security policy. If 
             enabled, no other security can be enabled."
       DEFVAL { disable }
       ::= { bsnDot11EssEntry 47 }

bsnDot11EssL2tpSecurity OBJECT-TYPE
        SYNTAX INTEGER { enable (1),disable (0)}
        MAX-ACCESS read-create
        STATUS current
        DESCRIPTION
            "Status of L2TP security policy. Note that this cannot be 
             applied with Web security policy, Cranite or Fortress 
             policy."
        DEFVAL { disable }
        ::= { bsnDot11EssEntry 49 }

bsnDot11EssWPAAuthPresharedKeyHex OBJECT-TYPE
        SYNTAX OCTET STRING (SIZE(0..40))
                MAX-ACCESS read-create
        STATUS deprecated
        DESCRIPTION
                "WPA Authentication Preshared Key in the hex format.
                 This applies only when bsnDot11EssWPAAuthKeyMgmtMode 
                 is in enable state.
                This has been deprecated for cLWSecDot11EssCckmTable."
    ::= { bsnDot11EssEntry 50 }

bsnDot11EssBroadcastSsid OBJECT-TYPE
        SYNTAX INTEGER { enable (1),disable (0)}
        MAX-ACCESS read-create
        STATUS current
        DESCRIPTION
            "This attribute when enabled allows the switch to 
             broadcast this SSID."
        DEFVAL { enable }
        ::= { bsnDot11EssEntry 51 }

bsnDot11EssExternalPolicyValidation OBJECT-TYPE
        SYNTAX INTEGER { enabled (1),disabled (0)}
        MAX-ACCESS read-create
        STATUS current
        DESCRIPTION
            "This attribute specifies if external policy servers will 
             be used for validation. If no servers are configured in 
             bsnExternalPolicyServerTable then it cannot be enabled."
        DEFVAL { enabled }
        ::= { bsnDot11EssEntry 52 }

bsnDot11EssRSNSecurity OBJECT-TYPE
        SYNTAX INTEGER { enable (1),disable (0)}
        MAX-ACCESS read-create
        STATUS deprecated
        DESCRIPTION
            "This attribute specifies status of RSN Security Policy.
             This has been deprecated for cLWSecDot11EssCckmTable."
        DEFVAL { disable }
        ::= { bsnDot11EssEntry 53 }

bsnDot11EssRSNWPACompatibilityMode OBJECT-TYPE
        SYNTAX INTEGER { enable (1),disable (0)}
        MAX-ACCESS read-create
        STATUS deprecated
        DESCRIPTION
            "This attribute specifies RSN security's compatibility 
             mode with WPA.
             This has been deprecated for cLWSecDot11EssCckmTable."
        DEFVAL { disable }
        ::= { bsnDot11EssEntry 54 }

bsnDot11EssRSNAllowTKIPClients OBJECT-TYPE
        SYNTAX INTEGER { yes (1),no (0)}
        MAX-ACCESS read-create
        STATUS deprecated
        DESCRIPTION
            "This attribute specifies whether TKIP clients are allowed 
             by RSN Policy.
             This has been deprecated for cLWSecDot11EssCckmTable."
        DEFVAL { no }
        ::= { bsnDot11EssEntry 55 }

bsnDot11EssRSNAuthKeyMgmtMode OBJECT-TYPE
        SYNTAX INTEGER { enable (1),disable (0)}
        MAX-ACCESS read-create
        STATUS deprecated
        DESCRIPTION
            "This attribute specifies whether Preshared key is used or
             not. If used user should specify a key between 8 and 63 
             characters in bsnDot11EssRSNAuthPresharedKey attribute.
             This has been deprecated for cLWSecDot11EssCckmTable."
        DEFVAL { disable }
        ::= { bsnDot11EssEntry 56 }

bsnDot11EssRSNAuthPresharedKey OBJECT-TYPE
        SYNTAX OCTET STRING (SIZE(8..63))
                MAX-ACCESS read-create
        STATUS deprecated
        DESCRIPTION
               "RSN Authentication Preshared Key. This applies only 
                when bsnDot11EssRSNAuthKeyMgmtMode is in enable state.
                This has been deprecated for cLWSecDot11EssCckmTable."
    ::= { bsnDot11EssEntry 57 }

bsnDot11EssRSNAuthPresharedKeyHex OBJECT-TYPE
        SYNTAX OCTET STRING (SIZE(0..40))
                MAX-ACCESS read-create
        STATUS deprecated
        DESCRIPTION
                "RSN Authentication Preshared Key in the hex format.
                 This applies only when bsnDot11EssWPAAuthKeyMgmtMode 
                 is in enable state.
                This has been deprecated for cLWSecDot11EssCckmTable."
    ::= { bsnDot11EssEntry 58 }
        
bsnDot11EssIPv6Bridging OBJECT-TYPE
    SYNTAX INTEGER { disable (0), enable (1) }
    MAX-ACCESS read-create
    STATUS current
    DESCRIPTION
        "When enabled, IPv6 bridging is applied on the packets."
    DEFVAL { disable }
    ::= {  bsnDot11EssEntry 59 }

bsnDot11EssRowStatus OBJECT-TYPE
        SYNTAX RowStatus
        MAX-ACCESS read-create
        STATUS current
        DESCRIPTION
                "A row status type for the bsnDot11EssEntry"
    ::= { bsnDot11EssEntry 60 }

bsnDot11EssWmePolicySetting OBJECT-TYPE
    SYNTAX INTEGER { disable (0), allowed (1), 
                     required (2), invalid (3) }
    MAX-ACCESS read-create
    STATUS current
    DESCRIPTION
        "When enabled, WME Policy is applied on the packets."
    DEFVAL { disable }
    ::= {  bsnDot11EssEntry 61 }

bsnDot11Ess80211ePolicySetting OBJECT-TYPE
    SYNTAX INTEGER { disable (0), allowed (1), 
                     required (2), invalid (3) }
    MAX-ACCESS read-create
    STATUS current
    DESCRIPTION
        "When enabled, 802.11e Policy is applied on the packets."
    DEFVAL { disable }
    ::= {  bsnDot11EssEntry 62 }

bsnDot11EssWebPassthroughEmail OBJECT-TYPE
    SYNTAX INTEGER { disable (0), enable (1) }
    MAX-ACCESS read-create
    STATUS current
    DESCRIPTION
        "When enabled, along with the bsnDot11EssWebPassthru attribute,
         the client is allowed to connect by entering his/her email 
         address on the web connection page. There is no further 
         authentication required."
    DEFVAL { disable }
    ::= {  bsnDot11EssEntry 63 }
    
bsnDot11Ess7920PhoneSupport OBJECT-TYPE
    SYNTAX INTEGER { disable (0), clientCacLimit(1), 
                     apCacLimit(2), both(3) }
    MAX-ACCESS read-create
    STATUS current
    DESCRIPTION
        "When client cac limit is enabled, the 7920 Phones with old 
         software where the Call Admission Control (CAC) Limit is 
         Specified on the client will be supported on the WLAN. The 
         support for clientCacLimit (by setting to value 1 or 3) cannot
         be enabled when the bsnDot11EssWmePolicySetting is set to 
         allowed or required. When ap cac limit is enabled, the 7920 
         Phones with new software where the Call Admission Control 
         (CAC) Limit is advertised by the AP, will be supported on the 
         WLAN."
    DEFVAL { disable }
    ::= {  bsnDot11EssEntry 64 }
    
bsnDot11EssRadiusAuthPrimaryServer OBJECT-TYPE
        SYNTAX DisplayString (SIZE(0..21))
        MAX-ACCESS read-create
        STATUS current
        DESCRIPTION
             "Primary Radius Authentication Server for this wlan."
    ::= { bsnDot11EssEntry 95 }

bsnDot11EssRadiusAuthSecondaryServer OBJECT-TYPE
        SYNTAX DisplayString (SIZE(0..21))
        MAX-ACCESS read-create
        STATUS current
        DESCRIPTION
             "Secondary Radius Authentication Server for this wlan."
    ::= { bsnDot11EssEntry 96 }

bsnDot11EssRadiusAuthTertiaryServer OBJECT-TYPE
        SYNTAX DisplayString (SIZE(0..21))
        MAX-ACCESS read-create
        STATUS current
        DESCRIPTION
             "Tertiary Radius Authentication Server for this wlan."
    ::= { bsnDot11EssEntry 97 }

bsnDot11EssRadiusAcctPrimaryServer OBJECT-TYPE
        SYNTAX DisplayString (SIZE(0..21))
        MAX-ACCESS read-create
        STATUS current
        DESCRIPTION
             "Primary Radius Accounting Server for this wlan."
    ::= { bsnDot11EssEntry 98 }

bsnDot11EssRadiusAcctSecondaryServer OBJECT-TYPE
        SYNTAX DisplayString (SIZE(0..21))
        MAX-ACCESS read-create
        STATUS current
        DESCRIPTION
             "Secondary Radius Accounting Server for this wlan."
    ::= { bsnDot11EssEntry 99 }

bsnDot11EssRadiusAcctTertiaryServer OBJECT-TYPE
        SYNTAX DisplayString (SIZE(0..21))
        MAX-ACCESS read-create
        STATUS current
        DESCRIPTION
             "Tertiary Radius Accounting Server for this wlan."
    ::= { bsnDot11EssEntry 100 }

-- ***************************************************************
-- * QOS Profile Table
-- ***************************************************************

bsnDot11QosProfileTable OBJECT-TYPE
    SYNTAX SEQUENCE OF BsnDot11QosProfileEntry
    MAX-ACCESS not-accessible
    STATUS current
    DESCRIPTION
        "QOS Profiles specified in bsnDot11EssTable can be customized 
         in this table. This is a lookup table for auto created 
         profiles"
    ::= { bsnEss 17 }

bsnDot11QosProfileEntry OBJECT-TYPE
    SYNTAX BsnDot11QosProfileEntry
    MAX-ACCESS not-accessible
    STATUS current
    DESCRIPTION
        "An entry in bsnDot11QosProfileTable."
    INDEX { bsnDot11QosProfileName }
    ::= { bsnDot11QosProfileTable 1 }

BsnDot11QosProfileEntry ::=
    SEQUENCE {
    bsnDot11QosProfileName                       OCTET STRING,
    bsnDot11QosProfileDesc                       OCTET STRING,
    bsnDot11QosAverageDataRate                   INTEGER,
    bsnDot11QosBurstDataRate                     INTEGER,
    bsnDot11QosAvgRealTimeDataRate               INTEGER,
    bsnDot11QosBurstRealTimeDataRate             INTEGER,
    bsnDot11QosMaxRFUsagePerAP                   INTEGER,
    bsnDot11QosProfileQueueDepth                 INTEGER,
    bsnDot11WiredQosProtocol                     INTEGER,
    bsnDot11802Dot1PTag                          INTEGER,
    bsnDot11ResetProfileToDefault                INTEGER
    }

bsnDot11QosProfileName OBJECT-TYPE
        SYNTAX OCTET STRING (SIZE(1..32))
        MAX-ACCESS read-only
        STATUS current
        DESCRIPTION
                "QOS Profile Name. This will be one of bronze,gold,
                 platinum,silver,uranium."
    ::= { bsnDot11QosProfileEntry 1 }

bsnDot11QosProfileDesc OBJECT-TYPE
        SYNTAX OCTET STRING (SIZE(1..64))
        MAX-ACCESS read-write
        STATUS current
        DESCRIPTION
                "QOS Profile Description."
    ::= { bsnDot11QosProfileEntry 2 }

bsnDot11QosAverageDataRate OBJECT-TYPE
        SYNTAX INTEGER(0..60000)
        MAX-ACCESS read-write
        STATUS current
        DESCRIPTION
                "This is one of the per user bandwidth contracts(k).
                 Specifies Average Data Rate per user. Value of 0 
                 indicates the feature is disabled."
    ::= { bsnDot11QosProfileEntry 3 }

bsnDot11QosBurstDataRate OBJECT-TYPE
        SYNTAX INTEGER(0..60000)
        MAX-ACCESS read-write
        STATUS current
        DESCRIPTION
                "This is one of the per user bandwidth contracts(k).
                 Specifies Average Burst Data Rate per user. Value of 
                 0 indicates the feature is disabled."
    ::= { bsnDot11QosProfileEntry 4 }

bsnDot11QosAvgRealTimeDataRate OBJECT-TYPE
        SYNTAX INTEGER(0..60000)
        MAX-ACCESS read-write
        STATUS current
        DESCRIPTION
                "This is one of the per user bandwidth contracts(k).
                 Specifies Average Real Time Data Rate per user. 
                 Value of 0 indicates the feature is disabled."
    ::= { bsnDot11QosProfileEntry 5 }

bsnDot11QosBurstRealTimeDataRate OBJECT-TYPE
        SYNTAX INTEGER(0..60000)
        MAX-ACCESS read-write
        STATUS current
        DESCRIPTION
                "This is one of the per user bandwidth contracts(k).
                 Specifies Burst Real Time Data Rate per user. Value 
                 of 0 indicates the feature is disabled."
    ::= { bsnDot11QosProfileEntry 6 }

bsnDot11QosMaxRFUsagePerAP OBJECT-TYPE
        SYNTAX INTEGER(1..100)
        MAX-ACCESS read-write
        STATUS current
        DESCRIPTION
                "This is one of the over the Air QOS parameter.
                 Specifies maximum RF Usage per AP in percentage."
    ::= { bsnDot11QosProfileEntry 7 }

bsnDot11QosProfileQueueDepth OBJECT-TYPE
        SYNTAX INTEGER(10..255)
        MAX-ACCESS read-write
        STATUS current
        DESCRIPTION
                "This is one of the over the Air QOS parameter.
                 Specifies Queue depth for the current profile."
    ::= { bsnDot11QosProfileEntry 8 }

bsnDot11WiredQosProtocol OBJECT-TYPE
        SYNTAX INTEGER { none(0),dot1p(1)}
        MAX-ACCESS read-write
        STATUS current
        DESCRIPTION
                "This is one of the over the Air QOS parameter.
                 Specifies Queue depth for the current profile."
    ::= { bsnDot11QosProfileEntry 9 }

bsnDot11802Dot1PTag OBJECT-TYPE
        SYNTAX INTEGER(0..7)
        MAX-ACCESS read-write
        STATUS current
        DESCRIPTION
                "Specifies the type of wired QOS protocol for the 
                 current profile. Value of 0 indicates the feature is 
                 disabled."
    ::= { bsnDot11QosProfileEntry 10 }

bsnDot11ResetProfileToDefault OBJECT-TYPE
    SYNTAX INTEGER { reset (1), default (0)}
    MAX-ACCESS read-write
    STATUS current
    DESCRIPTION
        "Set this attribute to reset to restore the factory default
         value for the profile."
    ::= {  bsnDot11QosProfileEntry 40 }    
    
-- ***************************************************************
-- * Mobile Station Index Table
-- ***************************************************************

bsnMobileStationTable OBJECT-TYPE
    SYNTAX SEQUENCE OF BsnMobileStationEntry
    MAX-ACCESS not-accessible
    STATUS current
    DESCRIPTION
        "Mobile Station Table indexed by bsnMobileStationMacAddress.
        (Mobile Station is better referred to as Client in the current
         releases.)"
    ::= { bsnEss 4 }

bsnMobileStationEntry OBJECT-TYPE
    SYNTAX BsnMobileStationEntry
    MAX-ACCESS not-accessible
    STATUS current
    DESCRIPTION
        "An entry in bsnMobileStationTable."
    INDEX { bsnMobileStationMacAddress }
    ::= { bsnMobileStationTable 1 }

BsnMobileStationEntry ::=
    SEQUENCE {
        bsnMobileStationMacAddress                      MacAddress,
        bsnMobileStationIpAddress                       IpAddress,
        bsnMobileStationUserName                        DisplayString,
        bsnMobileStationAPMacAddr                       MacAddress,
        bsnMobileStationAPIfSlotId                      INTEGER,
        bsnMobileStationEssIndex                        INTEGER,
        bsnMobileStationSsid                            DisplayString,
        bsnMobileStationAID                             Unsigned32,
        bsnMobileStationStatus                          INTEGER,
        bsnMobileStationReasonCode                      INTEGER,
        bsnMobileStationMobilityStatus                  INTEGER,
        bsnMobileStationAnchorAddress                   IpAddress,
        bsnMobileStationCFPollable                      INTEGER,
        bsnMobileStationCFPollRequest                   INTEGER,
        bsnMobileStationChannelAgilityEnabled           INTEGER,
        bsnMobileStationPBCCOptionImplemented           INTEGER,
        bsnMobileStationShortPreambleOptionImplemented  INTEGER,
        bsnMobileStationSessionTimeout                  Unsigned32,
        bsnMobileStationAuthenticationAlgorithm         INTEGER,
        bsnMobileStationWepState                        INTEGER,
        bsnMobileStationPortNumber                      Unsigned32,
        bsnMobileStationDeleteAction                    INTEGER,
        bsnMobileStationPolicyManagerState              DisplayString,
        bsnMobileStationSecurityPolicyStatus            INTEGER,
        bsnMobileStationProtocol                        INTEGER,
        bsnMobileStationMirrorMode                      INTEGER,
        bsnMobileStationInterface                       DisplayString,
        bsnMobileStationApMode                          INTEGER,
        bsnMobileStationVlanId                          Integer32,
        bsnMobileStationPolicyType                      INTEGER,
        bsnMobileStationEncryptionCypher                INTEGER,
        bsnMobileStationEapType                         INTEGER,
        bsnMobileStationCcxVersion                      INTEGER,
        bsnMobileStationE2eVersion                      INTEGER,
        bsnMobileStationStatusCode                      INTEGER
    }
bsnMobileStationMacAddress OBJECT-TYPE
        SYNTAX MacAddress
        MAX-ACCESS read-only
        STATUS current
        DESCRIPTION
                "802.11 MAC Address of the Mobile Station."
    ::= { bsnMobileStationEntry 1 }

bsnMobileStationIpAddress OBJECT-TYPE
        SYNTAX IpAddress
        MAX-ACCESS read-only
        STATUS current
        DESCRIPTION
                "IP Address of the Mobile Station"
    ::= { bsnMobileStationEntry 2 }

bsnMobileStationUserName OBJECT-TYPE
        SYNTAX DisplayString
        MAX-ACCESS read-only
        STATUS current
        DESCRIPTION
                "User Name,if any, of the Mobile Station. This would   
                 be non empty in case of Web Authentication and IPSec."
    ::= { bsnMobileStationEntry 3 }

bsnMobileStationAPMacAddr OBJECT-TYPE
        SYNTAX MacAddress
        MAX-ACCESS read-only
        STATUS current
        DESCRIPTION
                "802.11 Mac Address of the AP to which the
                 Mobile Station is associated."
    ::= { bsnMobileStationEntry 4 }

bsnMobileStationAPIfSlotId OBJECT-TYPE
        SYNTAX INTEGER(0..15)
        MAX-ACCESS read-only
        STATUS current
        DESCRIPTION
                "Slot ID of AP Interface to which the mobile station
                 is associated. The value 15 is used to indicate that 
                 the slot Id is invalid."
    ::= { bsnMobileStationEntry 5 }

bsnMobileStationEssIndex OBJECT-TYPE
        SYNTAX INTEGER(0..16)
        MAX-ACCESS read-only
        STATUS current
        DESCRIPTION
        "Ess Index of the Wlan(SSID) that is being used by Mobile 
         Station to connect to AP"
    ::= { bsnMobileStationEntry 6 }

bsnMobileStationSsid OBJECT-TYPE
        SYNTAX DisplayString
        MAX-ACCESS read-only
        STATUS current
        DESCRIPTION
                " The SSID Advertised by Mobile Station"
    ::= { bsnMobileStationEntry 7 }

bsnMobileStationAID OBJECT-TYPE
        SYNTAX Unsigned32
        MAX-ACCESS read-only
        STATUS current
        DESCRIPTION
                "AID for the mobile station"
    ::= { bsnMobileStationEntry 8 }


bsnMobileStationStatus OBJECT-TYPE
        SYNTAX INTEGER { 
                        idle (0),
                        aaaPending (1),
                        authenticated (2),
                        associated (3),
                        powersave (4),
                        disassociated (5),
                        tobedeleted (6),
                        probing(7),
                        blacklisted (8) 
                      }
        MAX-ACCESS read-only
                STATUS current
        DESCRIPTION
                "Status of the mobile station"
    ::= { bsnMobileStationEntry 9 }

bsnMobileStationReasonCode OBJECT-TYPE
        SYNTAX INTEGER { unspecified (1),
             previousAuthNotValid (2),
             deauthenticationLeaving (3),
             disassociationDueToInactivity (4),
             disassociationAPBusy (5),
             class2FrameFromNonAuthStation (6),
             class2FrameFromNonAssStation (7),
             disassociationStaHasLeft (8),
             staReqAssociationWithoutAuth (9),
             missingReasonCode (99)
    }
        MAX-ACCESS read-only
        STATUS current
        DESCRIPTION
                " Reason Code as defined by 802.11 standards"
    ::= { bsnMobileStationEntry 10 }


bsnMobileStationMobilityStatus OBJECT-TYPE
        SYNTAX INTEGER { unassociated(0),
                         local(1),
                         anchor(2),
                         foreign(3),
                         handoff(4),
                         unknown(5),
                         exportanchor(6),
                         exportforeign(7) }
        MAX-ACCESS read-only
        STATUS current
        DESCRIPTION
                "Mobility Role of the Mobile Station."
    ::= { bsnMobileStationEntry 11 }

bsnMobileStationAnchorAddress OBJECT-TYPE
        SYNTAX IpAddress
        MAX-ACCESS read-only
        STATUS current
        DESCRIPTION
                "If the Mobility Status of the Mobile Station is 
                 Anchor then it will have Peer Ip Address and will 
                 have Anchor IP if the Role is Foreign"
    ::= { bsnMobileStationEntry 12 }

bsnMobileStationCFPollable OBJECT-TYPE
    SYNTAX INTEGER { notimplemented(0),implemented(1)}
    MAX-ACCESS read-only
    STATUS current
    DESCRIPTION
            "When this attribute is true, it shall indicate that the 
             Mobile Station is able to respond to a CF-Poll with a 
             data frame within a SIFS time. This attribute shall be 
             false if the Mobile Station is not able to respond to a 
             CF-Poll with a data frame within a SIFS time."
    ::= { bsnMobileStationEntry 13 }

bsnMobileStationCFPollRequest OBJECT-TYPE
    SYNTAX INTEGER { notimplemented(0),implemented(1)}
    MAX-ACCESS read-only
    STATUS current
    DESCRIPTION
            "Specifies whether CFP is requested by Mobile
             Station or not"
    ::= { bsnMobileStationEntry 14 }

bsnMobileStationChannelAgilityEnabled OBJECT-TYPE
     SYNTAX INTEGER { notimplemented(0),implemented(1)}
     MAX-ACCESS read-only
     STATUS current
     DESCRIPTION
         "This attribute indicates that the PHY channel agility
          functionality is enabled."
    ::= { bsnMobileStationEntry 15 }

bsnMobileStationPBCCOptionImplemented OBJECT-TYPE
     SYNTAX INTEGER { notimplemented(0),implemented(1)}
     MAX-ACCESS read-only
     STATUS current
     DESCRIPTION
             "This attribute, when true, shall indicate that the PBCC
              modulation option as defined in subclause 18.4.6.6 is
              implemented.  The default value of this attribute shall
              be false."
    ::= { bsnMobileStationEntry 16 }

bsnMobileStationShortPreambleOptionImplemented OBJECT-TYPE
     SYNTAX INTEGER { notimplemented(0),implemented(1)}
     MAX-ACCESS read-only
     STATUS current
     DESCRIPTION
             "This attribute, when true, shall indicate that the
              short preamble option as defined in subclause 18.2.2.2
              is implemented.  The default value of this attribute
              shall be false."
    ::= { bsnMobileStationEntry 17 }


bsnMobileStationSessionTimeout OBJECT-TYPE
        SYNTAX Unsigned32
        MAX-ACCESS read-only
        STATUS current
        DESCRIPTION
                " Session Timeout of Mobile station"
    ::= { bsnMobileStationEntry 18 }

bsnMobileStationAuthenticationAlgorithm OBJECT-TYPE
        SYNTAX INTEGER { 
                        openSystem (0),
                        sharedKey(1), 
                        unknown(2), 
                        openAndEap(128) 
                       }
        MAX-ACCESS read-only
        STATUS current
        DESCRIPTION
                "Authentication Algorithm of Mobile Station "
    ::= { bsnMobileStationEntry 19}

bsnMobileStationWepState OBJECT-TYPE
        SYNTAX INTEGER {enable (1), disable(2)}
        MAX-ACCESS read-only
        STATUS current
        DESCRIPTION
                "WEP State of Mobile Station"
    ::= { bsnMobileStationEntry 20}

bsnMobileStationPortNumber OBJECT-TYPE
        SYNTAX Unsigned32
        MAX-ACCESS read-only
        STATUS current
        DESCRIPTION
                "The Port Number of this Airespace Switch on which the
                 traffic of the Mobile Station is coming through."
    ::= { bsnMobileStationEntry 21 }

bsnMobileStationDeleteAction OBJECT-TYPE
        SYNTAX INTEGER {default(0),delete(1)}
        MAX-ACCESS read-write
        STATUS current
        DESCRIPTION
                "Action to Deauthenticate the Mobile Station. Set the 
                 State to delete."
    ::= { bsnMobileStationEntry 22}

bsnMobileStationPolicyManagerState OBJECT-TYPE
        SYNTAX DisplayString
        MAX-ACCESS read-only
        STATUS current
        DESCRIPTION
                "Policy Manager State of the mobile station."
    ::= { bsnMobileStationEntry 23 }

bsnMobileStationSecurityPolicyStatus OBJECT-TYPE
    SYNTAX INTEGER { completed(0),notcompleted(1)}
    MAX-ACCESS read-only
    STATUS current
    DESCRIPTION
            "When this attribute has value completed, it shall
             indicate that the Mobile Station has completed the 
             security policy checks. Otherwise the checks are yet
             to be completed."
    ::= { bsnMobileStationEntry 24 }

bsnMobileStationProtocol OBJECT-TYPE
        SYNTAX INTEGER { 
                        dot11a (1),
                        dot11b(2),
                        dot11g(3), 
                        unknown(4),
                        mobile(5)
                       }
        MAX-ACCESS read-only
        STATUS current
        DESCRIPTION
                "The 802.11 protocol type of the client. The protocol 
                 is mobile when this client detail is seen on the 
                 anchor i.e it's mobility status is anchor."
    ::= { bsnMobileStationEntry 25}

bsnMobileStationMirrorMode OBJECT-TYPE
    SYNTAX INTEGER { disable (0), enable (1) }
    MAX-ACCESS read-write
    STATUS current
    DESCRIPTION
        "If enabled, then mirroring for this client will be statically
         configured irrespective of the AP and the port this client 
         is on."
    ::= {  bsnMobileStationEntry 26 }

bsnMobileStationInterface OBJECT-TYPE
        SYNTAX     DisplayString (SIZE(0..32))
        MAX-ACCESS read-only
        STATUS     current
        DESCRIPTION
            "Name of the Interface of the mobile client to the switch."
    ::= { bsnMobileStationEntry 27 }

bsnMobileStationApMode OBJECT-TYPE
    SYNTAX INTEGER { 
                     local (0),
                     monitor (1), 
                     remote(2), 
                     roguedetector(3) 
                   }
    MAX-ACCESS read-only
    STATUS current
    DESCRIPTION
        "Mode of the AP to which the Mobile Station is associated."
    ::= {  bsnMobileStationEntry 28 }

bsnMobileStationVlanId OBJECT-TYPE
        SYNTAX Integer32 (0..4096)
        MAX-ACCESS read-only
        STATUS current
        DESCRIPTION
                "Vlan ID of the Interface to which the client is 
                 associated."
    ::= { bsnMobileStationEntry 29 }

bsnMobileStationPolicyType OBJECT-TYPE
    SYNTAX INTEGER { dot1x (0), wpa1 (1), 
                     wpa2(2), wpa2vff(3), 
                     notavailable(4), unknown(5) }
    MAX-ACCESS read-only
    STATUS current
    DESCRIPTION
        "Mode of the AP to which the Mobile Station is associated."
    ::= {  bsnMobileStationEntry 30 }

bsnMobileStationEncryptionCypher OBJECT-TYPE
    SYNTAX INTEGER { ccmpAes (0), tkipMic (1), 
                     wep40(2), wep104(3), 
                     wep128(4), none(5), 
                     notavailable(6), unknown(7) }
    MAX-ACCESS read-only
    STATUS current
    DESCRIPTION
        "Mode of the AP to which the Mobile Station is associated."
    ::= {  bsnMobileStationEntry 31 }

bsnMobileStationEapType OBJECT-TYPE
    SYNTAX INTEGER { eapTls (0), ttls (1), 
                     peap(2), leap(3), 
                     speke(4), eapFast(5), 
                     notavailable(6), unknown(7)}
    MAX-ACCESS read-only
    STATUS current
    DESCRIPTION
        "Mode of the AP to which the Mobile Station is associated."
    ::= {  bsnMobileStationEntry 32 }

bsnMobileStationCcxVersion OBJECT-TYPE
    SYNTAX INTEGER { notSupported (0), 
                     ccxv1 (1),
                     ccxv2(2), 
                     ccxv3(3),
                     ccxv4(4), 
                     ccxv5(5) }
    MAX-ACCESS read-only
    STATUS current
    DESCRIPTION
        "Represents the Cisco Compatible Extensions (CCX)
         Version the client is using for communication
         with the AP."
    DEFVAL { notSupported }
    ::= {  bsnMobileStationEntry 33 }

bsnMobileStationE2eVersion OBJECT-TYPE
    SYNTAX INTEGER { notSupported (0),
                     e2ev1 (1), 
                     e2ev2(2) }
    MAX-ACCESS read-only
    STATUS current
    DESCRIPTION
        "Represents the End-2-End Version the client is
         using for communication with the AP."
    DEFVAL { notSupported }
    ::= {  bsnMobileStationEntry 34 }

bsnMobileStationStatusCode OBJECT-TYPE
        SYNTAX INTEGER(0..65535)
        MAX-ACCESS read-only
        STATUS current
        DESCRIPTION
                " Status Code of the Mobile Station"
    ::= { bsnMobileStationEntry 42 }

-- ***************************************************************
-- * Mobile Station Table Indexed by Mobile Station IpAddress
-- ***************************************************************

bsnMobileStationByIpTable OBJECT-TYPE
    SYNTAX SEQUENCE OF BsnMobileStationByIpEntry
    MAX-ACCESS not-accessible
    STATUS current
    DESCRIPTION
        "Mobile Station Table indexed by bsnMobileStationByIpAddress. 
         NOTE: This is just to facilitate the search of mobile 
         stations based on IP Address. Doing a get without the index 
         doesn't return anything.  (Mobile Station is better referred 
         to as Client in the current releases.)"
    ::= { bsnEss 10 }

bsnMobileStationByIpEntry OBJECT-TYPE
    SYNTAX BsnMobileStationByIpEntry
    MAX-ACCESS not-accessible
    STATUS current
    DESCRIPTION
        "An entry in bsnMobileStationByIpTable."
    INDEX { bsnMobileStationByIpAddress }
    ::= { bsnMobileStationByIpTable 1 }

BsnMobileStationByIpEntry ::=
    SEQUENCE {
        bsnMobileStationByIpAddress       IpAddress,
        bsnMobileStationByIpMacAddress    MacAddress
    }

bsnMobileStationByIpAddress OBJECT-TYPE
        SYNTAX IpAddress
        MAX-ACCESS read-only
        STATUS current
        DESCRIPTION
                "IP Address of the Mobile Station"
    ::= { bsnMobileStationByIpEntry 1 }

bsnMobileStationByIpMacAddress OBJECT-TYPE
        SYNTAX MacAddress
        MAX-ACCESS read-only
        STATUS current
        DESCRIPTION
                "802.11 Mac Address of the Mobile Station."
    ::= { bsnMobileStationByIpEntry 2 }

-- ***************************************************************
-- * Mobile Station Table Indexed by Mobile Station Username and MAC 
-- * Address
-- ***************************************************************

bsnMobileStationByUsernameTable OBJECT-TYPE
    SYNTAX SEQUENCE OF BsnMobileStationByUsernameEntry
    MAX-ACCESS not-accessible
    STATUS current
    DESCRIPTION
        "Mobile Station Table indexed by the Mobile Station Username 
         and MAC Address. NOTE: This is just to facilitate the search 
         of mobile stations based on User Name. Doing a get without 
         the username doesn't return anything. (Mobile Station is 
         better referred to as Client in the current releases.)"
    ::= { bsnEss 13 }

bsnMobileStationByUsernameEntry OBJECT-TYPE
    SYNTAX BsnMobileStationByUsernameEntry
    MAX-ACCESS not-accessible
    STATUS current
    DESCRIPTION
        "An entry in bsnMobileStationByUsernameTable."
    INDEX { bsnMobileStationByUserName,  
            bsnMobileStationByUserMacAddress}
    ::= { bsnMobileStationByUsernameTable 1 }

BsnMobileStationByUsernameEntry ::=
    SEQUENCE {
        bsnMobileStationByUserName              OCTET STRING,
        bsnMobileStationByUserMacAddress        MacAddress
    }

bsnMobileStationByUserName OBJECT-TYPE
        SYNTAX OCTET STRING (SIZE(1..64))
        MAX-ACCESS read-only
        STATUS current
        DESCRIPTION
                "Username of the Mobile Station"
    ::= { bsnMobileStationByUsernameEntry 1 }

bsnMobileStationByUserMacAddress OBJECT-TYPE
        SYNTAX MacAddress
        MAX-ACCESS read-only
        STATUS current
        DESCRIPTION
                "802.11 Mac Address of the Mobile Station."
    ::= { bsnMobileStationByUsernameEntry 2 }


-- *****************************************************************
-- *  Airespace Mobile Station Per Radio Per Vap Table
-- *****************************************************************

bsnMobileStationPerRadioPerVapTable OBJECT-TYPE
    SYNTAX SEQUENCE OF BsnMobileStationPerRadioPerVapEntry
    MAX-ACCESS not-accessible
    STATUS current
    DESCRIPTION
        "Mobile Station Per Radio Per VAP(WLAN) Table. This table 
         lists all Mobile Stations on a particular Airespace AP 
         Interface for a particular ESS(Wlan). It only lists MAC 
         Addresses. Further details for a Mobile Station can be found 
         from bsnMobileStationTable once the MAC Address is knonwn.
         (Mobile Station is better referred to as Client in the 
          current releases.)"
    ::= { bsnEss 5 }

bsnMobileStationPerRadioPerVapEntry OBJECT-TYPE
    SYNTAX BsnMobileStationPerRadioPerVapEntry
    MAX-ACCESS not-accessible
    STATUS current
    DESCRIPTION
        "An entry in MobileStationPerRadioPerVapTable."
    INDEX { bsnAPDot3MacAddress, bsnAPIfSlotId, bsnDot11EssIndex,
            bsnMobileStationPerRadioPerVapIndex }
           
    ::= { bsnMobileStationPerRadioPerVapTable 1 }

BsnMobileStationPerRadioPerVapEntry ::=
    SEQUENCE {
    bsnMobileStationPerRadioPerVapIndex      Integer32,
    bsnMobileStationMacAddr                  MacAddress
    }

bsnMobileStationPerRadioPerVapIndex OBJECT-TYPE
        SYNTAX Integer32
        MAX-ACCESS read-only
        STATUS current
        DESCRIPTION
                " The index of  Mobile Station. The index starts from 
                  1 and goes upto the total number of Mobile Stations 
                  on Airespace Radio Interface for a specific 
                  ESS (Wlan)."
    ::= { bsnMobileStationPerRadioPerVapEntry 1 }

bsnMobileStationMacAddr OBJECT-TYPE
        SYNTAX MacAddress
        MAX-ACCESS read-only
        STATUS current
        DESCRIPTION
                "The MAC Address of Mobile Station."
    ::= { bsnMobileStationPerRadioPerVapEntry 20 }

-- *******************************************************************
-- * Begin of bsnMobileStationStatsTable
-- *******************************************************************

bsnMobileStationStatsTable OBJECT-TYPE
    SYNTAX SEQUENCE OF BsnMobileStationStatsEntry
    MAX-ACCESS not-accessible
    STATUS current
    DESCRIPTION
        "Mobile Station Statistics Table.
        (Mobile Station is better referred to as Client in the current 
         releases.)"
    ::= { bsnEss 6 }

bsnMobileStationStatsEntry OBJECT-TYPE
    SYNTAX BsnMobileStationStatsEntry
    MAX-ACCESS not-accessible
    STATUS current
    DESCRIPTION
        "An entry in bsnMobileStationStatsTable."
    INDEX { bsnMobileStationMacAddress }
    ::= { bsnMobileStationStatsTable 1 }

BsnMobileStationStatsEntry ::=
    SEQUENCE {
        bsnMobileStationRSSI                      Integer32,
        bsnMobileStationBytesReceived             Counter64,
        bsnMobileStationBytesSent                 Counter64,
        bsnMobileStationPolicyErrors              Counter64,
        bsnMobileStationPacketsReceived           Counter64,
        bsnMobileStationPacketsSent               Counter64,
        bsnMobileStationSnr                       Integer32
    }

bsnMobileStationRSSI OBJECT-TYPE
        SYNTAX Integer32
        MAX-ACCESS read-only
        STATUS current
        DESCRIPTION
                "Average packet RSSI for the Mobile Station."
    ::= { bsnMobileStationStatsEntry 1}

bsnMobileStationBytesReceived OBJECT-TYPE
        SYNTAX Counter64
        MAX-ACCESS read-only
        STATUS current
        DESCRIPTION
                "Bytes received from Mobile Station"
    ::= { bsnMobileStationStatsEntry 2}

bsnMobileStationBytesSent OBJECT-TYPE
        SYNTAX Counter64
        MAX-ACCESS read-only
        STATUS current
        DESCRIPTION
                "Bytes sent to Mobile Station"
    ::= { bsnMobileStationStatsEntry 3}

bsnMobileStationPolicyErrors OBJECT-TYPE
        SYNTAX Counter64
        MAX-ACCESS read-only
        STATUS current
        DESCRIPTION
                "Number of Policy Errors for Mobile Station"
    ::= { bsnMobileStationStatsEntry 4}

bsnMobileStationPacketsReceived OBJECT-TYPE
        SYNTAX Counter64
        MAX-ACCESS read-only
        STATUS current
        DESCRIPTION
                "Packets received from Mobile Station"
    ::= { bsnMobileStationStatsEntry 5}

bsnMobileStationPacketsSent OBJECT-TYPE
        SYNTAX Counter64
        MAX-ACCESS read-only
        STATUS current
        DESCRIPTION
                "Packets sent to Mobile Station"
    ::= { bsnMobileStationStatsEntry 6}

bsnMobileStationSnr OBJECT-TYPE
        SYNTAX Integer32
        MAX-ACCESS read-only
        STATUS current
        DESCRIPTION
                "Signal to noise Ratio of the Mobile Station."
    ::= { bsnMobileStationStatsEntry 26}

-- *******************************************************************
-- * Begin of bsnMobileStationExtStatsTable
-- *******************************************************************

bsnMobileStationExtStatsTable OBJECT-TYPE
    SYNTAX SEQUENCE OF BsnMobileStationExtStatsEntry
    MAX-ACCESS not-accessible
    STATUS current
    DESCRIPTION
        "Mobile Station Extended Statistics Table.
        (Mobile Station is better referred to as Client in the 
         current releases.)"
    ::= { bsnEss 21 }

bsnMobileStationExtStatsEntry OBJECT-TYPE
    SYNTAX BsnMobileStationExtStatsEntry
    MAX-ACCESS not-accessible
    STATUS current
    DESCRIPTION
        "An entry in bsnMobileStationExtStatsTable."
    INDEX { bsnMobileStationMacAddress }
    ::= { bsnMobileStationExtStatsTable 1 }

BsnMobileStationExtStatsEntry ::=
    SEQUENCE {
    bsnMobileStationSampleTime                Integer32,
    bsnMobileStationTxExcessiveRetries        Counter64,
    bsnMobileStationTxRetries                 Counter64,
    bsnMobileStationTxFiltered                Counter64
    }

bsnMobileStationSampleTime OBJECT-TYPE
        SYNTAX Integer32
        MAX-ACCESS read-only
        STATUS current
        DESCRIPTION
                "Time stats were sampled as seconds since the epoch."
    ::= { bsnMobileStationExtStatsEntry 1}

bsnMobileStationTxExcessiveRetries OBJECT-TYPE
        SYNTAX Counter64
        MAX-ACCESS read-only
        STATUS current
        DESCRIPTION
                "Tx packets dropped due to excessive retries."
    ::= { bsnMobileStationExtStatsEntry 2}

bsnMobileStationTxRetries OBJECT-TYPE
        SYNTAX Counter64
        MAX-ACCESS read-only
        STATUS current
        DESCRIPTION
                "Tx packets retransmitted."
    ::= { bsnMobileStationExtStatsEntry 3}

bsnMobileStationTxFiltered OBJECT-TYPE
        SYNTAX Counter64
        MAX-ACCESS read-only
        STATUS current
        DESCRIPTION
                "Tx packets dropped by the built-in Tx filter"
    ::= { bsnMobileStationExtStatsEntry 20}

-- ***************************************************************
-- * Mobile Station RSSI data Table
-- ***************************************************************

bsnMobileStationRssiDataTable OBJECT-TYPE
    SYNTAX SEQUENCE OF BsnMobileStationRssiDataEntry
    MAX-ACCESS not-accessible
    STATUS current
    DESCRIPTION
        "Mobile Station RSSI data Table indexed by 
         bsnMobileStationMacAddress, 
         bsnMobileStationRssiDataApMacAddress, 
         bsnMobileStationRssiDataApIfSlotId.
         (Mobile Station is better referred to as Client in the 
          current releases.)"
    ::= { bsnEss 11 }

bsnMobileStationRssiDataEntry OBJECT-TYPE
    SYNTAX BsnMobileStationRssiDataEntry
    MAX-ACCESS not-accessible
    STATUS current
    DESCRIPTION
        "An entry in bsnMobileStationRssiDataTable."
    INDEX { bsnMobileStationMacAddress, 
            bsnMobileStationRssiDataApMacAddress, 
            bsnMobileStationRssiDataApIfSlotId,
            bsnAPIfPhyAntennaIndex
          }
    ::= { bsnMobileStationRssiDataTable 1 }

BsnMobileStationRssiDataEntry ::=
    SEQUENCE {
        bsnMobileStationRssiDataApMacAddress       MacAddress,
        bsnMobileStationRssiDataApIfSlotId         Unsigned32,
        bsnMobileStationRssiDataApIfType           INTEGER,
        bsnMobileStationRssiDataApName             DisplayString,
        bsnMobileStationRssiData                   Integer32,
        bsnAPIfPhyAntennaIndex                     Unsigned32,
        bsnMobileStationRssiDataLastHeard          Counter32
    }

bsnMobileStationRssiDataApMacAddress OBJECT-TYPE
        SYNTAX MacAddress
        MAX-ACCESS read-only
        STATUS current
        DESCRIPTION
                "802.11 Mac Address of the AP on which
                Mobile Station is associated."
    ::= { bsnMobileStationRssiDataEntry 1 }

bsnMobileStationRssiDataApIfSlotId OBJECT-TYPE
        SYNTAX Unsigned32(0..15)
        MAX-ACCESS read-only
        STATUS current
        DESCRIPTION
                "SlotId of APIf on which mobile station is
                 associated"
    ::= { bsnMobileStationRssiDataEntry 2 }

bsnMobileStationRssiDataApIfType OBJECT-TYPE
        SYNTAX INTEGER { dot11bg(1),dot11a(2),unknown(3)}
        MAX-ACCESS read-only
        STATUS current
        DESCRIPTION
                " The interface type of the radio that sensed the 
                  rssi data."
    ::= { bsnMobileStationRssiDataEntry 3 }

bsnMobileStationRssiDataApName OBJECT-TYPE
        SYNTAX DisplayString
        MAX-ACCESS read-only
        STATUS current
        DESCRIPTION
                "The Name of the AP that sensed the rssi data."
    ::= { bsnMobileStationRssiDataEntry 4 }

bsnMobileStationRssiData OBJECT-TYPE
        SYNTAX Integer32
        MAX-ACCESS read-only
        STATUS current
        DESCRIPTION
        " RSSI seen by Airespace AP Interface for the Mobile Station"
    ::= { bsnMobileStationRssiDataEntry 5 }

bsnAPIfPhyAntennaIndex OBJECT-TYPE
     SYNTAX      Unsigned32
     MAX-ACCESS  read-only
     STATUS      current
     DESCRIPTION
          "Antenna which recived the probe request from client.
           The antenna which reported the RSSI value for the client.
           For now value will be 0 to 1, in future it may change."
        ::= { bsnMobileStationRssiDataEntry 6 }

bsnMobileStationRssiDataLastHeard OBJECT-TYPE
        SYNTAX Counter32
        MAX-ACCESS read-only
        STATUS current
        DESCRIPTION
                "No of seconds ago when this RSSI data was recorded."
    ::= { bsnMobileStationRssiDataEntry 25 }

-- ***************************************************************
-- * RF ID Tag Table
-- ***************************************************************

bsnTagTable OBJECT-TYPE
    SYNTAX SEQUENCE OF BsnTagEntry
    MAX-ACCESS not-accessible
    STATUS current
    DESCRIPTION
        "RF ID Tag Table indexed by bsnTagDot11MacAddress."
    ::= { bsnEss 18 }

bsnTagEntry OBJECT-TYPE
    SYNTAX BsnTagEntry
    MAX-ACCESS not-accessible
    STATUS current
    DESCRIPTION
        "An entry in bsnTagTable."
    INDEX { bsnTagDot11MacAddress }
    ::= { bsnTagTable 1 }

BsnTagEntry ::=
    SEQUENCE {
        bsnTagDot11MacAddress                  MacAddress,
        bsnTagType                             INTEGER,
        bsnTagTimeInterval                     Unsigned32,
        bsnTagBatteryStatus                    INTEGER,
        bsnTagLastReported                     Unsigned32
    }

bsnTagDot11MacAddress OBJECT-TYPE
        SYNTAX MacAddress
        MAX-ACCESS read-only
        STATUS current
        DESCRIPTION
                "802.11 MAC Address of the RF ID Tag."
    ::= { bsnTagEntry 1 }

bsnTagType OBJECT-TYPE
        SYNTAX INTEGER { unknown(0),type1(2)}
        MAX-ACCESS read-only
        STATUS current
        DESCRIPTION
                "Type of the RF ID Tag."
    ::= { bsnTagEntry 2 }

bsnTagTimeInterval OBJECT-TYPE
        SYNTAX Unsigned32
        MAX-ACCESS read-only
        STATUS current
        DESCRIPTION
                "Time Interval after which the tag transmits data."
    ::= { bsnTagEntry 3 }

bsnTagBatteryStatus OBJECT-TYPE
        SYNTAX INTEGER { unknown(0), low(1),
                         normal(2), medium(3)}
        MAX-ACCESS read-only
        STATUS current
        DESCRIPTION
                "Battery Status of the RF ID Tag."
    ::= { bsnTagEntry 4 }

bsnTagLastReported OBJECT-TYPE
        SYNTAX Unsigned32
        MAX-ACCESS read-only
        STATUS current
        DESCRIPTION
                "No of seconds ago when this tag was heard by any AP."
    ::= { bsnTagEntry 23 }

-- *******************************************************************
-- * Begin of bsnTagStatsTable
-- *******************************************************************

bsnTagStatsTable OBJECT-TYPE
    SYNTAX SEQUENCE OF BsnTagStatsEntry
    MAX-ACCESS not-accessible
    STATUS current
    DESCRIPTION
        "RF ID Tag Statistics Table."
    ::= { bsnEss 20 }

bsnTagStatsEntry OBJECT-TYPE
    SYNTAX BsnTagStatsEntry
    MAX-ACCESS not-accessible
    STATUS current
    DESCRIPTION
        "An entry in bsnTagStatsTable."
    INDEX { bsnTagDot11MacAddress }
    ::= { bsnTagStatsTable 1 }

BsnTagStatsEntry ::=
    SEQUENCE {
        bsnTagBytesReceived            Unsigned32,
        bsnTagPacketsReceived          Unsigned32
    }

bsnTagBytesReceived OBJECT-TYPE
        SYNTAX Unsigned32
        MAX-ACCESS read-only
        STATUS current
        DESCRIPTION
                "Bytes received from an RF ID Tag"
    ::= { bsnTagStatsEntry 1}

bsnTagPacketsReceived OBJECT-TYPE
        SYNTAX Unsigned32
        MAX-ACCESS read-only
        STATUS current
        DESCRIPTION
                "Packets received from an RF ID Tag"
    ::= { bsnTagStatsEntry 20}

-- ***************************************************************
-- * RF ID Tag Detecting AP Table
-- ***************************************************************

bsnTagRssiDataTable OBJECT-TYPE
    SYNTAX SEQUENCE OF BsnTagRssiDataEntry
    MAX-ACCESS not-accessible
    STATUS current
    DESCRIPTION
        "RF ID Tag Detecting AP Table indexed by bsnTagDot11MacAddress,
         bsnTagRssiDataApMacAddress and bsnTagRssiDataApIfSlotId."
    ::= { bsnEss 19 }

bsnTagRssiDataEntry OBJECT-TYPE
    SYNTAX BsnTagRssiDataEntry
    MAX-ACCESS not-accessible
    STATUS current
    DESCRIPTION
        "An entry in bsnTagRssiDataTable."
    INDEX { bsnTagDot11MacAddress, 
            bsnTagRssiDataApMacAddress,
            bsnTagRssiDataApIfSlotId }
    ::= { bsnTagRssiDataTable 1 }

BsnTagRssiDataEntry ::=
    SEQUENCE {
        bsnTagRssiDataApMacAddress         MacAddress,
        bsnTagRssiDataApIfSlotId           Unsigned32,
        bsnTagRssiDataApIfType             INTEGER,
        bsnTagRssiDataApName               DisplayString,
        bsnTagRssiDataLastHeard            Counter32,
        bsnTagRssiData                     Integer32,
        bsnTagRssiDataSnr                  Integer32
    }

bsnTagRssiDataApMacAddress OBJECT-TYPE
        SYNTAX MacAddress
        MAX-ACCESS read-only
        STATUS current
        DESCRIPTION
        "802.11 MAC Address of the AP detecting the RF ID Tag."
    ::= { bsnTagRssiDataEntry 1 }

bsnTagRssiDataApIfSlotId OBJECT-TYPE
        SYNTAX Unsigned32(0..5)
        MAX-ACCESS read-only
        STATUS current
        DESCRIPTION
        "Slot Id of the radio on AP detecting the RF ID Tag."
    ::= { bsnTagRssiDataEntry 2 }

bsnTagRssiDataApIfType OBJECT-TYPE
    SYNTAX INTEGER { dot11b (1), dot11a (2),uwb (4) }
    MAX-ACCESS read-only
    STATUS current
    DESCRIPTION
        "Interface Type of the radio on AP detecting the RF ID Tag."
    ::= { bsnTagRssiDataEntry 3 }

bsnTagRssiDataApName OBJECT-TYPE
    SYNTAX DisplayString (SIZE(0..32))
    MAX-ACCESS read-only
    STATUS current
    DESCRIPTION
        "Name of the AP detecting the RF ID Tag."
    ::= {  bsnTagRssiDataEntry 4 }

bsnTagRssiDataLastHeard OBJECT-TYPE
        SYNTAX Counter32
        MAX-ACCESS read-only
        STATUS current
        DESCRIPTION
        "No of seconds ago when this tag was heard by this detecting 
         AP."
    ::= { bsnTagRssiDataEntry 5 }

bsnTagRssiData OBJECT-TYPE
        SYNTAX Integer32
        MAX-ACCESS read-only
        STATUS current
        DESCRIPTION
                "RSSI of the RF ID Tag as seen by the radio on this 
                 detecting AP."
    ::= { bsnTagRssiDataEntry 6 }

bsnTagRssiDataSnr OBJECT-TYPE
        SYNTAX Integer32
        MAX-ACCESS read-only
        STATUS current
        DESCRIPTION
                "SNR of the RF ID tag as seen by the radio on this 
                 detecting AP."
    ::= { bsnTagRssiDataEntry 26 }

--********************************************************************
-- * Begin of bsnWatchListClientTable
--********************************************************************

bsnWatchListClientTable OBJECT-TYPE
    SYNTAX SEQUENCE OF BsnWatchListClientEntry
    MAX-ACCESS not-accessible
    STATUS obsolete
    DESCRIPTION
        "Table of watch listed clients. When clients are added to this 
         table by username or MAC address, ACS collects data for them 
         to show trend reports. The switch generates Client
         Association and Client Authentication traps for the watch 
         listed clients.The watch list feature can be enbaled or 
         diabled by the bsnWatchListFeatureEnable flag on the switch."
    ::= { bsnEss 12 }

bsnWatchListClientEntry OBJECT-TYPE
    SYNTAX BsnWatchListClientEntry
    MAX-ACCESS not-accessible
    STATUS obsolete
    DESCRIPTION
        "An entry in bsnWatchListClientTable."
    INDEX { bsnWatchListClientKey, bsnWatchListClientType }
    ::= { bsnWatchListClientTable 1 }

BsnWatchListClientEntry ::=
    SEQUENCE {
        bsnWatchListClientKey          OCTET STRING,
        bsnWatchListClientType         INTEGER,
        bsnWatchListClientRowStatus    RowStatus
    }

bsnWatchListClientKey OBJECT-TYPE
        SYNTAX OCTET STRING (SIZE(1..64))
        MAX-ACCESS read-create
        STATUS obsolete
        DESCRIPTION
                " MAC Address or User Name of Client that is to be 
                  added to the watch list."
    ::= { bsnWatchListClientEntry 1 }

bsnWatchListClientType OBJECT-TYPE
        SYNTAX INTEGER { byMac(1),byUserName(2)}
        MAX-ACCESS read-create
        STATUS obsolete
        DESCRIPTION
                "The type of the watch list client entry. The entry can
                 be created by Client MAC Address or by Username."
    ::= { bsnWatchListClientEntry 2 }

bsnWatchListClientRowStatus OBJECT-TYPE
        SYNTAX RowStatus
        MAX-ACCESS read-create
        STATUS obsolete
        DESCRIPTION
                "A row status type for the bsnWatchListClientEntry"
    ::= { bsnWatchListClientEntry 20 }


-- ********************************************************************
-- * Begin of bsnRougueAPTable
--********************************************************************

bsnRogueAPTable OBJECT-TYPE
    SYNTAX SEQUENCE OF BsnRogueAPEntry
    MAX-ACCESS not-accessible
    STATUS current
    DESCRIPTION
        "Rogue Table. This table lists all the Rogue APs detected by 
         Airespace APs."
    ::= { bsnEss 7 }

bsnRogueAPEntry OBJECT-TYPE
    SYNTAX BsnRogueAPEntry
    MAX-ACCESS not-accessible
    STATUS current
    DESCRIPTION
        "An Entry in bsnRogueAPTable."
    INDEX {bsnRogueAPDot11MacAddress}
    ::= { bsnRogueAPTable 1 }

BsnRogueAPEntry ::=
    SEQUENCE {
          bsnRogueAPDot11MacAddress          MacAddress,
          bsnRogueAPTotalDetectingAPs        Integer32,
          bsnRogueAPFirstReported            DisplayString,
          bsnRogueAPLastReported             DisplayString,
          bsnRogueAPContainmentLevel         INTEGER,
          bsnRogueAPType                     INTEGER,
          bsnRogueAPOnNetwork                INTEGER,
          bsnRogueAPTotalClients             Integer32,
          bsnRogueAPRowStatus                RowStatus,
          bsnRogueAPMaxDetectedRSSI          Integer32,
          bsnRogueAPSSID                     DisplayString,
          bsnRogueAPState                    INTEGER
        }

bsnRogueAPDot11MacAddress OBJECT-TYPE
        SYNTAX MacAddress
        MAX-ACCESS read-create
        STATUS current
        DESCRIPTION
                "MAC Address of Rogue Station."
    ::= { bsnRogueAPEntry 1 }

bsnRogueAPTotalDetectingAPs OBJECT-TYPE
        SYNTAX Integer32
        MAX-ACCESS read-only
        STATUS current
        DESCRIPTION
              "Total number of Airespace APs that detected this rogue."
    ::= { bsnRogueAPEntry 2 }

bsnRogueAPFirstReported OBJECT-TYPE
        SYNTAX DisplayString
        MAX-ACCESS read-only
        STATUS current
        DESCRIPTION
                "Time Stamp when this Rogue was First Detected."
    ::= { bsnRogueAPEntry 3 }

bsnRogueAPLastReported OBJECT-TYPE
        SYNTAX DisplayString
        MAX-ACCESS read-only
        STATUS current
        DESCRIPTION
                "Time Stamp when this Rogue was Last Detected."
    ::= { bsnRogueAPEntry 4 }

bsnRogueAPContainmentLevel OBJECT-TYPE
        SYNTAX INTEGER { unassigned(0),level1(1),
                        level2(2),level3(3),level4(4) }
        MAX-ACCESS read-create
        STATUS current
        DESCRIPTION
              "If the state of the rogue is contained, this specifies
               the level of containment. Higher the level, more the 
               number of detecting APs that are used to contain it.
               The value must be between 1 to 4 for 'contained' state."
    ::= { bsnRogueAPEntry 5 }

bsnRogueAPType OBJECT-TYPE
        SYNTAX INTEGER { ap(0),adhoc(1)}
        MAX-ACCESS read-only
        STATUS current
        DESCRIPTION
               "This attribute specifies if the Rogue is of ad-hoc type
                or is an AP."
    ::= { bsnRogueAPEntry 6 }

bsnRogueAPOnNetwork OBJECT-TYPE
        SYNTAX INTEGER { no(0),yes(1)}
        MAX-ACCESS read-only
        STATUS current
        DESCRIPTION
                "This attribute specifies if the Rogue is on Wired 
                 Network or not."
    ::= { bsnRogueAPEntry 7 }

bsnRogueAPTotalClients OBJECT-TYPE
        SYNTAX Integer32
        MAX-ACCESS read-only
        STATUS current
        DESCRIPTION
                " Total number of Clients detected on this rogue."
    ::= { bsnRogueAPEntry 8 }

bsnRogueAPRowStatus OBJECT-TYPE
        SYNTAX RowStatus
        MAX-ACCESS read-create
        STATUS current
        DESCRIPTION
                "Row Status"
    ::= { bsnRogueAPEntry 9 }

bsnRogueAPMaxDetectedRSSI   OBJECT-TYPE
        SYNTAX        Integer32
        MAX-ACCESS    read-only
        STATUS        current
        DESCRIPTION
                "This is the max RSSI value of all the detctecting APs,
                 which have detected this rogue. "
    ::= { bsnRogueAPEntry 10 }
         
bsnRogueAPSSID    OBJECT-TYPE
        SYNTAX        DisplayString (SIZE(1..32))
        MAX-ACCESS    read-only
        STATUS        current
        DESCRIPTION
                "This is the SSID of the rogue detected by Access 
                 Point, which has max RSSI value of all the 
                 detectecting APs of this rogue."
    ::= { bsnRogueAPEntry 11 }

bsnRogueAPState OBJECT-TYPE
        SYNTAX INTEGER { initializing(0), 
                         pending(1),
                         alert(2),
                         detectedLrad(3),
                         known(4),
                         acknowledge(5),
                         contained(6), 
                         threat(7),
                         containedPending(8), 
                         knownContained(9),
                         trustedMissing(10) 
                       }
        MAX-ACCESS read-create
        STATUS current
        DESCRIPTION
                "This attribute is use to specify the state in which 
                 the Rogue AP is user can set the Rogue AP in alert, 
                 known or acknowledge state.
                 Alert state means Rogue AP can be a potential threat.
                 Trap will be sent out to trap recipients. 
                 Known state means its just internal AP which is not 
                 on the same Switch.  
                 Acknowledge state means an external AP whose
                 existence is acceptable and not a threat (probably 
                 some other company's AP).
                 Contained means containement is initiated and ongoing.
                 Threat is usually the state when the rogue is found 
                 on wired network.
                 known(4), knownContained(9) and trustedMissing(10) 
                 will appear in known rogue list.
                 known rogues can be pre provisioned and known rogues 
                 state can be changed to alert(2)"
    ::= { bsnRogueAPEntry 24 }


--********************************************************************
--* Begin of bsnRougueAPAirespaceAPTable
--********************************************************************

bsnRogueAPAirespaceAPTable OBJECT-TYPE
    SYNTAX SEQUENCE OF BsnRogueAPAirespaceAPEntry
    MAX-ACCESS not-accessible
    STATUS current
    DESCRIPTION
        "Rogue Station Table. This table lists all the Airespace AP 
         Interfaces that detected a particular Rogue."
    ::= { bsnEss 8 }

bsnRogueAPAirespaceAPEntry OBJECT-TYPE
    SYNTAX BsnRogueAPAirespaceAPEntry
    MAX-ACCESS not-accessible
    STATUS current
    DESCRIPTION
        "An entry in bsnRogueAPAirespaceAPEntry."
    INDEX { bsnRogueAPDot11MacAddress,
            bsnRogueAPAirespaceAPMacAddress,
            bsnRogueAPAirespaceAPSlotId }
    ::= { bsnRogueAPAirespaceAPTable 1 }

BsnRogueAPAirespaceAPEntry ::=
    SEQUENCE {
        bsnRogueAPAirespaceAPMacAddress          MacAddress,
        bsnRogueAPAirespaceAPSlotId              Unsigned32,
        bsnRogueAPRadioType                      INTEGER,
        bsnRogueAPAirespaceAPName                DisplayString,
        bsnRogueAPChannelNumber                  Integer32,
        bsnRogueAPSsid                           DisplayString,
        bsnRogueAPAirespaceAPRSSI                Integer32,
        bsnRogueAPContainmentMode                INTEGER,
        bsnRogueAPContainmentChannelCount        Unsigned32,
        bsnRogueAPContainmentChannels            DisplayString,
        bsnRogueAPAirespaceAPLastHeard           Counter32,
        bsnRogueAPAirespaceAPWepMode             INTEGER,
        bsnRogueAPAirespaceAPPreamble            INTEGER,
        bsnRogueAPAirespaceAPWpaMode             INTEGER,
        bsnRogueAPAirespaceAPSNR                 Integer32
        }

bsnRogueAPAirespaceAPMacAddress OBJECT-TYPE
        SYNTAX MacAddress
        MAX-ACCESS read-only
        STATUS current
        DESCRIPTION
            "MAC Address of Airespace AP Interface that Detected 
             the Rogue."
    ::= { bsnRogueAPAirespaceAPEntry 1 }

bsnRogueAPAirespaceAPSlotId OBJECT-TYPE
    SYNTAX Unsigned32(0..2)
    MAX-ACCESS read-only
    STATUS current
    DESCRIPTION
        "The slot ID of the Airespace AP Interface that detected the 
         Rogue."
    ::= { bsnRogueAPAirespaceAPEntry 2 }

bsnRogueAPRadioType OBJECT-TYPE
        SYNTAX INTEGER { dot11b(1),dot11a(2),unknown(3)}
        MAX-ACCESS read-only
        STATUS current
        DESCRIPTION
            "The Airespace AP Interface type that detected the Rogue."
    ::= { bsnRogueAPAirespaceAPEntry 3 }


bsnRogueAPAirespaceAPName OBJECT-TYPE
        SYNTAX DisplayString
        MAX-ACCESS read-only
        STATUS current
        DESCRIPTION
            "Name of Airespace AP Interface that detected the Rogue."
    ::= { bsnRogueAPAirespaceAPEntry 4 }


bsnRogueAPChannelNumber OBJECT-TYPE
        SYNTAX Integer32
        MAX-ACCESS read-only
        STATUS current
        DESCRIPTION
            " The advertised Channel Number of the Airespace AP 
              Interface picked up from the Rogue."
    ::= { bsnRogueAPAirespaceAPEntry 5 }

bsnRogueAPSsid OBJECT-TYPE
        SYNTAX DisplayString
        MAX-ACCESS read-only
        STATUS current
        DESCRIPTION
            " The SSID Advertised by Rogue Station."
    ::= { bsnRogueAPAirespaceAPEntry 6 }


bsnRogueAPAirespaceAPRSSI OBJECT-TYPE
        SYNTAX Integer32
        MAX-ACCESS read-only
        STATUS current
        DESCRIPTION
            "Rogue RSSI as seen by Airespace AP Interface."
    ::= { bsnRogueAPAirespaceAPEntry 7 }

bsnRogueAPContainmentMode OBJECT-TYPE
        SYNTAX INTEGER { invalid(0),deauthBroadcast(1),
                        cfp(2),max(3),unknown(99)}
        MAX-ACCESS read-only
        STATUS current
        DESCRIPTION
                "If the rogue is in 'contained' state, this attribute
                 shows the containment mode used by the AP."
    ::= { bsnRogueAPAirespaceAPEntry 8 }

bsnRogueAPContainmentChannelCount OBJECT-TYPE
    SYNTAX Unsigned32
    MAX-ACCESS read-only
    STATUS current
    DESCRIPTION
        "The number of channels used for rogue containment."
    ::= { bsnRogueAPAirespaceAPEntry 9 }

bsnRogueAPContainmentChannels OBJECT-TYPE
    SYNTAX DisplayString
    MAX-ACCESS read-only
    STATUS current
    DESCRIPTION
        "This is the comma separated string of channels used for 
         rogue containment."
    ::= { bsnRogueAPAirespaceAPEntry 10 }

bsnRogueAPAirespaceAPLastHeard OBJECT-TYPE
        SYNTAX Counter32
        MAX-ACCESS read-only
        STATUS current
        DESCRIPTION
                "No of seconds ago when this Rogue was last heard by 
                 this AP. "
    ::= { bsnRogueAPAirespaceAPEntry 11 }

bsnRogueAPAirespaceAPWepMode OBJECT-TYPE
        SYNTAX INTEGER { disabled(0),enabled(1)}
        MAX-ACCESS read-only
        STATUS current
        DESCRIPTION
                "The WEP mode on this detecting AP."
    ::= { bsnRogueAPAirespaceAPEntry 12 }

bsnRogueAPAirespaceAPPreamble OBJECT-TYPE
        SYNTAX INTEGER { long(0),short(1)}
        MAX-ACCESS read-only
        STATUS current
        DESCRIPTION
                "The Preamble on this detecting AP."
    ::= { bsnRogueAPAirespaceAPEntry 13 }

bsnRogueAPAirespaceAPWpaMode OBJECT-TYPE
        SYNTAX INTEGER { disabled(0),enabled(1)}
        MAX-ACCESS read-only
        STATUS current
        DESCRIPTION
                "The WPA mode on this detecting AP."
    ::= { bsnRogueAPAirespaceAPEntry 14 }

bsnRogueAPAirespaceAPSNR OBJECT-TYPE
        SYNTAX Integer32
        MAX-ACCESS read-only
        STATUS current
        DESCRIPTION
                "SNR seen by Airespace AP Interface from Rogue"
    ::= { bsnRogueAPAirespaceAPEntry 27 }


-- *****************************************************************
-- *  bsnRogueClientPerRogueAPTable
-- *****************************************************************

bsnRogueClientPerRogueAPTable OBJECT-TYPE
    SYNTAX SEQUENCE OF BsnRogueClientPerRogueAPEntry
    MAX-ACCESS not-accessible
    STATUS current
    DESCRIPTION
        "Rogue Clients for each rogue. This table lists all Rogue 
         Clients on a particular Rogue."
    ::= { bsnEss 16 }

bsnRogueClientPerRogueAPEntry OBJECT-TYPE
    SYNTAX BsnRogueClientPerRogueAPEntry
    MAX-ACCESS not-accessible
    STATUS current
    DESCRIPTION
        "An entry in RogueClientPerRogueAPTable."
    INDEX { bsnRogueAPDot11MacAddr, bsnRogueClientDot11MacAddr }
    ::= { bsnRogueClientPerRogueAPTable 1 }

BsnRogueClientPerRogueAPEntry ::=
    SEQUENCE {
    bsnRogueAPDot11MacAddr       MacAddress,
    bsnRogueClientDot11MacAddr   MacAddress
    }

bsnRogueAPDot11MacAddr OBJECT-TYPE
        SYNTAX MacAddress
        MAX-ACCESS read-only
        STATUS current
        DESCRIPTION
                "The MAC Address of the Rogue AP."
    ::= { bsnRogueClientPerRogueAPEntry 1 }

bsnRogueClientDot11MacAddr OBJECT-TYPE
        SYNTAX MacAddress
        MAX-ACCESS read-only
        STATUS current
        DESCRIPTION
                "MAC Address of the Rogue Client."
    ::= { bsnRogueClientPerRogueAPEntry 20 }

--********************************************************************
--* Begin of bsnRougueClientTable
--********************************************************************

bsnRogueClientTable OBJECT-TYPE
    SYNTAX SEQUENCE OF BsnRogueClientEntry
    MAX-ACCESS not-accessible
    STATUS current
    DESCRIPTION
        "Rogue Client Table. This table lists all the Rogue Clients 
         detected by Airespace APs."
    ::= { bsnEss 14 }

bsnRogueClientEntry OBJECT-TYPE
    SYNTAX BsnRogueClientEntry
    MAX-ACCESS not-accessible
    STATUS current
    DESCRIPTION
        "An Entry in bsnRogueClientTable."
    INDEX { bsnRogueClientDot11MacAddress }
    ::= { bsnRogueClientTable 1 }

BsnRogueClientEntry ::=
    SEQUENCE {
        bsnRogueClientDot11MacAddress          MacAddress,
        bsnRogueClientTotalDetectingAPs        Integer32,
        bsnRogueClientFirstReported            DisplayString,
        bsnRogueClientLastReported             DisplayString,
        bsnRogueClientBSSID                    MacAddress,
        bsnRogueClientContainmentLevel         INTEGER,
        bsnRogueClientLastHeard                Integer32,
        bsnRogueClientState                    INTEGER
        
        }

bsnRogueClientDot11MacAddress OBJECT-TYPE
        SYNTAX MacAddress
        MAX-ACCESS not-accessible
        STATUS current
        DESCRIPTION
                "Mac Address of Rogue Station."
    ::= { bsnRogueClientEntry 1 }

bsnRogueClientTotalDetectingAPs OBJECT-TYPE
        SYNTAX Integer32
        MAX-ACCESS read-only
        STATUS current
        DESCRIPTION
                "Total number of Airespace APs that detected this 
                 rogue."
    ::= { bsnRogueClientEntry 2 }

bsnRogueClientFirstReported OBJECT-TYPE
        SYNTAX DisplayString
        MAX-ACCESS read-only
        STATUS current
        DESCRIPTION
                "Time Stamp when this Rogue was First Detected."
    ::= { bsnRogueClientEntry 3 }

bsnRogueClientLastReported OBJECT-TYPE
        SYNTAX DisplayString
        MAX-ACCESS read-only
        STATUS current
        DESCRIPTION
                "Time Stamp when this Rogue was Last Detected."
    ::= { bsnRogueClientEntry 4 }

bsnRogueClientBSSID OBJECT-TYPE
        SYNTAX MacAddress
        MAX-ACCESS read-only
        STATUS current
        DESCRIPTION
                "This attribute specifies BSSID of the Rogue Client."
    ::= { bsnRogueClientEntry 5 }

bsnRogueClientContainmentLevel OBJECT-TYPE
        SYNTAX INTEGER { unassigned(0),level1(1),
                        level2(2),level3(3),level4(4)}
        MAX-ACCESS read-write
        STATUS current
        DESCRIPTION
                "If the state of the rogue is contained, this specifies
                 the level of containment.  Higher the level, more the
                 number of detecting APs that are used to contain it.
                 The value must be between 1 to 4 for 'contained' 
                 state."
    ::= { bsnRogueClientEntry 6 }

bsnRogueClientLastHeard OBJECT-TYPE
        SYNTAX Integer32
        MAX-ACCESS read-only
        STATUS current
        DESCRIPTION
                "Number of seconds ago this rogue client was detected."
    ::= { bsnRogueClientEntry 7 }

bsnRogueClientState OBJECT-TYPE
        SYNTAX INTEGER { initializing(0),pending(1),
                        alert(2),contained(6),
                        threat(7),containedpending(8) }
        MAX-ACCESS read-write
        STATUS current
        DESCRIPTION
                "This attribute is use to specify the state in which 
                 the Rogue AP is. User can set the Rogue Client in 
                 alert,known or acknowledge state.
                 Alert state means Rogue Client can be a potential i
                 threat.Trap will be sent out to trap recipients. 
                 Known state means its just internal Client which is 
                 not on the same Switch. 
                 Acknowledge state means an external Client whose
                 existence is acceptable and not a threat
                 (probably some other company's AP).
                 Contained means containement is initiated and 
                 ongoing"
    ::= { bsnRogueClientEntry 24 }

--********************************************************************
-- * Begin of bsnRougueAPTable
--********************************************************************

bsnRogueClientAirespaceAPTable OBJECT-TYPE
    SYNTAX SEQUENCE OF BsnRogueClientAirespaceAPEntry
    MAX-ACCESS not-accessible
    STATUS current
    DESCRIPTION
        "Rogue Station Table. This table lists all the Airespace AP 
         Interface that detected a particular Rogue."
    ::= { bsnEss 15 }

bsnRogueClientAirespaceAPEntry OBJECT-TYPE
    SYNTAX BsnRogueClientAirespaceAPEntry
    MAX-ACCESS not-accessible
    STATUS current
    DESCRIPTION
        "An entry in bsnRogueClientAirespaceAPEntry."
    INDEX { bsnRogueClientDot11MacAddress,
            bsnRogueClientAirespaceAPMacAddress,
            bsnRogueClientAirespaceAPSlotId }
    ::= { bsnRogueClientAirespaceAPTable 1 }

BsnRogueClientAirespaceAPEntry ::=
    SEQUENCE {
        bsnRogueClientAirespaceAPMacAddress          MacAddress,
        bsnRogueClientAirespaceAPSlotId              Unsigned32,
        bsnRogueClientRadioType                      INTEGER,
        bsnRogueClientAirespaceAPName                DisplayString,
        bsnRogueClientChannelNumber                  Integer32,
        bsnRogueClientAirespaceAPRSSI                Integer32,
        bsnRogueClientAirespaceAPLastHeard           DisplayString,
        bsnRogueClientAirespaceAPSNR                 Integer32
        }

bsnRogueClientAirespaceAPMacAddress OBJECT-TYPE
        SYNTAX MacAddress
        MAX-ACCESS read-only
        STATUS current
        DESCRIPTION
                "Mac Address of Airespace AP Interface that Detected 
                 the Rogue."
    ::= { bsnRogueClientAirespaceAPEntry 1 }

bsnRogueClientAirespaceAPSlotId OBJECT-TYPE
    SYNTAX Unsigned32(0..2)
    MAX-ACCESS read-only
    STATUS current
    DESCRIPTION
        "The slotId of the Airespace AP Interface that detected the 
         Rogue."
    ::= { bsnRogueClientAirespaceAPEntry 2 }

bsnRogueClientRadioType OBJECT-TYPE
        SYNTAX INTEGER { dot11b(1),dot11a(2),unknown(3)}
        MAX-ACCESS read-only
        STATUS current
        DESCRIPTION
                "The advertised SSID that the Airespace AP Interface 
                 picked up from the Rogue."
    ::= { bsnRogueClientAirespaceAPEntry 3 }


bsnRogueClientAirespaceAPName OBJECT-TYPE
        SYNTAX DisplayString
        MAX-ACCESS read-only
        STATUS current
        DESCRIPTION
                "Name of Airespace AP Interface that detected the 
                 Rogue."
    ::= { bsnRogueClientAirespaceAPEntry 4 }


bsnRogueClientChannelNumber OBJECT-TYPE
        SYNTAX Integer32
        MAX-ACCESS read-only
        STATUS current
        DESCRIPTION
                "The advertised Channel Number of that the Airespace 
                 AP Interface picked up from the Rogue."
    ::= { bsnRogueClientAirespaceAPEntry 5 }


bsnRogueClientAirespaceAPRSSI OBJECT-TYPE
        SYNTAX Integer32
        MAX-ACCESS read-only
        STATUS current
        DESCRIPTION
                " RSSI seen by Airespace AP Interface from the Rogue"
    ::= { bsnRogueClientAirespaceAPEntry 7 }


bsnRogueClientAirespaceAPLastHeard OBJECT-TYPE
        SYNTAX DisplayString
        MAX-ACCESS read-only
        STATUS current
        DESCRIPTION
                "No of seconds ago when this Rogue was last heard by 
                 this AP. "
    ::= { bsnRogueClientAirespaceAPEntry 11 }


bsnRogueClientAirespaceAPSNR OBJECT-TYPE
        SYNTAX Integer32
        MAX-ACCESS read-only
        STATUS current
        DESCRIPTION
                "SNR seen by Airespace AP Interface from Rogue"
    ::= { bsnRogueClientAirespaceAPEntry 27 }

--********************************************************************
-- * End of bsnRougueStationTable
--********************************************************************


--********************************************************************
-- * Begin of bsnThirdPartyAPTable
--********************************************************************

bsnThirdPartyAPTable OBJECT-TYPE
      SYNTAX     SEQUENCE OF BsnThirdPartyAPEntry
      MAX-ACCESS not-accessible
      STATUS     obsolete
      DESCRIPTION
            "Third Party Access Point Table. An entry needs to be 
             configured in this table for a third party access point 
             that needs to be supported by the Switch. Note: A third
             party ESS (Wlan) with ID 17 should be created in 
             bsnDot11EssTable before adding entries here.
             Please also note that ACS currently supports only 
             Aironet 350, 1200 and Orinoco 2000 Access Points as 
             third party APs."
      ::= { bsnEss 9 }

bsnThirdPartyAPEntry OBJECT-TYPE
      SYNTAX     BsnThirdPartyAPEntry
      MAX-ACCESS not-accessible
      STATUS     obsolete
      DESCRIPTION
            "An entry in bsnThirdPartyAPTable."
      INDEX      { bsnThirdPartyAPMacAddress }
      ::= { bsnThirdPartyAPTable 1 }

BsnThirdPartyAPEntry ::= SEQUENCE {
      bsnThirdPartyAPMacAddress       MacAddress,
      bsnThirdPartyAPInterface        Integer32,
      bsnThirdPartyAPIpAddress        IpAddress,
      bsnThirdPartyAP802Dot1XRequired INTEGER,
      bsnThirdPartyAPMirrorMode       INTEGER,
      bsnThirdPartyAPRowStatus        RowStatus
}

bsnThirdPartyAPMacAddress OBJECT-TYPE
      SYNTAX     MacAddress
      MAX-ACCESS read-create
      STATUS     obsolete
      DESCRIPTION
             "MAC Address of Third Party Access Point which is 
              connected directly to this Airespace Switch."
      ::= { bsnThirdPartyAPEntry 1 }

bsnThirdPartyAPInterface OBJECT-TYPE
      SYNTAX     Integer32
      MAX-ACCESS read-create
      STATUS     obsolete
      DESCRIPTION
             "Interface(Port Number) to which the Third Party AP is 
              connected."
      ::= { bsnThirdPartyAPEntry 2 }

bsnThirdPartyAPIpAddress OBJECT-TYPE
        SYNTAX IpAddress
        MAX-ACCESS read-create
        STATUS obsolete
        DESCRIPTION
             "Static IP address of the 3rd Party AP, 0.0.0.0 indicating
              x its using DHCP"
        DEFVAL { '00000000'H }
    ::= { bsnThirdPartyAPEntry 3 }

bsnThirdPartyAP802Dot1XRequired OBJECT-TYPE
    SYNTAX INTEGER { disable (0), enable (1)}
    MAX-ACCESS read-create
    STATUS obsolete
    DESCRIPTION
        "If 802.1X is required for the 3rd Party AP"
    DEFVAL { disable }
    ::= {  bsnThirdPartyAPEntry 4 }

bsnThirdPartyAPMirrorMode OBJECT-TYPE
    SYNTAX INTEGER { disable (0), enable (1) }
    MAX-ACCESS read-create
    STATUS obsolete
    DESCRIPTION
        "If enabled, then data from all the foreign AP users and all 
         the foreign APs on this APs port will be mirrored. These 
         clients are dynamically added to the switch's mirrored MAC 
         list."
    ::= {  bsnThirdPartyAPEntry 5 }

bsnThirdPartyAPRowStatus OBJECT-TYPE
      SYNTAX     RowStatus
      MAX-ACCESS read-create
      STATUS     obsolete
      DESCRIPTION
             "Row Status in the ThirdPartyAPEntry."
      ::= { bsnThirdPartyAPEntry 24 }

--********************************************************************
-- *  Airespace AP Table.
-- *  Rows in bsnAPTable are created by Airespace Switch as it 
-- *  discovers Airespace APs.
-- *  The MAC address of the 802.3 interface constitutes the index.
-- *
--********************************************************************

bsnAPTable OBJECT-TYPE
    SYNTAX SEQUENCE OF BsnAPEntry
    MAX-ACCESS not-accessible
    STATUS current
    DESCRIPTION
        "Table of Airespace APs managed by this Airespace Switch."
    ::= {  bsnAP 1 }

bsnAPEntry OBJECT-TYPE
    SYNTAX BsnAPEntry
    MAX-ACCESS not-accessible
    STATUS current
    DESCRIPTION
        "An entry in the bsnAPTable."
    INDEX { bsnAPDot3MacAddress }
    ::= { bsnAPTable 1 }

BsnAPEntry ::=
    SEQUENCE {
    bsnAPDot3MacAddress            MacAddress,
    bsnAPNumOfSlots                INTEGER,
    bsnAPName                      OCTET STRING,
    bsnApIpAddress                 IpAddress,
    bsnAPLocation                  OCTET STRING,
    bsnAPMonitorOnlyMode           INTEGER,
    bsnAPOperationStatus           INTEGER,
    bsnAPSoftwareVersion           DisplayString,
    bsnAPBootVersion               DisplayString,
    bsnAPPrimaryMwarName           OCTET STRING,
    bsnAPReset                     INTEGER,
    bsnAPStatsTimer                INTEGER,
    bsnAPPortNumber                INTEGER,
    bsnAPModel                     DisplayString,
    bsnAPSerialNumber              DisplayString,
    bsnAPClearConfig               INTEGER,
    bsnAPMirrorMode                INTEGER,
    bsnAPRemoteModeSupport         INTEGER,
    bsnAPType                      INTEGER,
    bsnAPSecondaryMwarName         OCTET STRING,
    bsnAPTertiaryMwarName          OCTET STRING,
    bsnAPIsStaticIP                INTEGER,
    bsnAPNetmask                   IpAddress,
    bsnAPGateway                   IpAddress,
    bsnAPStaticIPAddress           IpAddress,
    bsnAPBridgingSupport           INTEGER,
    bsnAPGroupVlanName             OCTET STRING,
    bsnAPAdminStatus               INTEGER,
    bsnAPIOSVersion                DisplayString,
    bsnAPCertificateType           INTEGER,
    bsnAPEthernetMacAddress        MacAddress
    }

bsnAPDot3MacAddress OBJECT-TYPE
    SYNTAX MacAddress
    MAX-ACCESS read-only
    STATUS current
    DESCRIPTION
        "The MAC address of an AP."
    ::= { bsnAPEntry 1 }

bsnAPNumOfSlots OBJECT-TYPE
    SYNTAX INTEGER(0..24)
    MAX-ACCESS read-only
    STATUS current
    DESCRIPTION
        "Number of Radio Interfaces on the Airespace AP.
         Currently maximum two interfaces are supported.
         One would be of type 802.11a and other of type
         802.11b/g."
    ::= {  bsnAPEntry 2 }

bsnAPName OBJECT-TYPE
    SYNTAX OCTET STRING (SIZE(0..32))
    MAX-ACCESS read-write
    STATUS current
    DESCRIPTION
        "Name assigned to this AP. If an AP is not configured its
         factory default name will be ap:<last three byte of 
         MACAddress> eg. ap:af:12:be"
    ::= {  bsnAPEntry 3 }

bsnAPLocation OBJECT-TYPE
    SYNTAX OCTET STRING (SIZE(0..80))
    MAX-ACCESS read-write
    STATUS current
    DESCRIPTION
        "User specified location of this AP.
         While configuring AP, user should specify a location for
         the AP so that its easy to figure out for some one where
         the AP is located."
    ::= {  bsnAPEntry 4 }

bsnAPMonitorOnlyMode OBJECT-TYPE
    SYNTAX INTEGER { local (0), monitor (1), remote(2), 
                     roguedetector(3), sniffer(4), bridge(5) }
    MAX-ACCESS read-write
    STATUS current
    DESCRIPTION
        "Monitor Only Mode Setting."
    ::= {  bsnAPEntry 5 }

bsnAPOperationStatus OBJECT-TYPE
    SYNTAX INTEGER {associated (1),disassociating (2), 
                    downloading(3) }
    MAX-ACCESS read-only
    STATUS current
    DESCRIPTION
        "Operation State of the AP. When AP associates with the 
         Airespace Switch its state will be associated. When Airespace
         AP is disassociated from the Switch, its state will be 
         disassociating. The state is downloading when the AP is 
         downloading its firmware."
    ::= {  bsnAPEntry 6 }

bsnAPSoftwareVersion OBJECT-TYPE
    SYNTAX DisplayString
    MAX-ACCESS read-only
    STATUS current
    DESCRIPTION
        "Major Minor Software Version of AP"
    ::= {  bsnAPEntry 8 }

bsnAPBootVersion OBJECT-TYPE
    SYNTAX DisplayString
    MAX-ACCESS read-only
    STATUS current
    DESCRIPTION
        "Major Minor Boot Version of AP"
    ::= {  bsnAPEntry 9 }

bsnAPPrimaryMwarName OBJECT-TYPE
    SYNTAX OCTET STRING (SIZE(0..31))
    MAX-ACCESS read-write
    STATUS current
    DESCRIPTION
     "sysName of the Airespace Switch which is suppose to be the
      Primary MWAR(switch) of the AP with which AP should associate.
      This work when AP is not directly connected to Airespace Switch,
      it tries to find Primary Switch and associates with it. If
      this attribute is left empty or AP is not able to find the 
      Airespace Switch with this name, then it will associate with 
      Secondary Switch."
    ::= {  bsnAPEntry 10 }

bsnAPReset OBJECT-TYPE
    SYNTAX INTEGER { reset (1), default (0)}
    MAX-ACCESS read-write
    STATUS current
    DESCRIPTION
     "Set this attribute to reset the AP.
      When it comes up it will try to associate with the
      Primary Switch if that is set, else it will associate with the
      Master Switch. Reading this attribute will always return 0"
    ::= {  bsnAPEntry 11 }

bsnAPStatsTimer OBJECT-TYPE
    SYNTAX INTEGER(0..65535)
    MAX-ACCESS read-write
    STATUS current
    DESCRIPTION
    "Configures the time interval in secs after which 
     bsnAPDot11Counters Stats is sent from AP to Switch. If not 
     configured this value is 0 which means never send the stats."
    ::= {  bsnAPEntry 12 }

bsnAPPortNumber OBJECT-TYPE
    SYNTAX INTEGER(0..65535)
    MAX-ACCESS read-only
    STATUS current
    DESCRIPTION
       "Port on the Switch on which this APs traffic is coming 
       through."
    ::= {  bsnAPEntry 13 }

bsnAPModel OBJECT-TYPE
    SYNTAX DisplayString
    MAX-ACCESS read-only
    STATUS current
    DESCRIPTION
    "AP Model"
    ::= {  bsnAPEntry 16 }

bsnAPSerialNumber OBJECT-TYPE
    SYNTAX DisplayString
    MAX-ACCESS read-only
    STATUS current
    DESCRIPTION
    "AP Serial Number."
    ::= {  bsnAPEntry 17 }

bsnAPClearConfig OBJECT-TYPE
    SYNTAX INTEGER { clear (1), default (0)}
    MAX-ACCESS read-write
    STATUS current
    DESCRIPTION
        "Set this attribute to clear AP configuration
         and reset it to factory defaults.
         Reading this attribute will always return 0"
    ::= {  bsnAPEntry 18 }

bsnApIpAddress OBJECT-TYPE
        SYNTAX IpAddress
        MAX-ACCESS read-write
        STATUS current
        DESCRIPTION
             "IP address of the AP. This will not be available when 
              the switch is operating in the Layer2 mode. In this case,
              the attribute will return 0 as value."
    ::= { bsnAPEntry 19 }

bsnAPMirrorMode OBJECT-TYPE
    SYNTAX INTEGER { disable (0), enable (1) }
    MAX-ACCESS read-write
    STATUS current
    DESCRIPTION
        "If enabled, then this AP's Client's Data is mirrored and this 
         AP's clients are dynamically added to the switch's mirrored 
         MAC list."
    ::= {  bsnAPEntry 20 }

bsnAPRemoteModeSupport OBJECT-TYPE
    SYNTAX INTEGER { disable (0), enable (1) }
    MAX-ACCESS read-only
    STATUS current
    DESCRIPTION
        "This specifies if the the Remote Mode is supported on this 
         AP or not. If supported user can set bsnAPMonitorOnlyMode to 
         remote. Otherwise not."
    ::= {  bsnAPEntry 21 }
    
bsnAPType OBJECT-TYPE
    SYNTAX INTEGER { ap1000 (1), ap1030 (2), 
                     mimo(3), unknown(4), ap1100(5),
                     ap1130(6), ap1240(7), ap1200(8),
                     ap1310(9), ap1500(10),
                     ap1250(11), ap1505(12) }
    MAX-ACCESS read-only
    STATUS current
    DESCRIPTION
        "This is the model of the AP in enumeration."
    ::= {  bsnAPEntry 22 }

bsnAPSecondaryMwarName OBJECT-TYPE
    SYNTAX OCTET STRING (SIZE(0..31))
    MAX-ACCESS read-write
    STATUS current
    DESCRIPTION
    "sysName of the Airespace Switch which is suppose to be the
     Secondary MWAR(switch) of the AP with which AP should associate
     if Primary Switch(configured through bsnAPPrimaryMwarName)  
     is not available. If primary and secondary switches are not 
     available then AP will associate with the tertiary switch."
    ::= {  bsnAPEntry 23 }

bsnAPTertiaryMwarName OBJECT-TYPE
    SYNTAX OCTET STRING (SIZE(0..31))
    MAX-ACCESS read-write
    STATUS current
    DESCRIPTION
    "sysName of the Airespace Switch which is suppose to be the
     Tertiary MWAR(switch) of the AP with which AP should associate.
     If primary,secondary and tertiary switch are not available 
     then it will associate with Master Switch."
    ::= {  bsnAPEntry 24 }
    
bsnAPIsStaticIP OBJECT-TYPE
    SYNTAX INTEGER { disable(0), enable(1) }
    MAX-ACCESS read-write
    STATUS current    DESCRIPTION
        "This flag when disabled implies that  AP will use DHCP to get 
         the IP address.  However, if it is enabled, then user should 
         enter the IPAddress, Netmask and Gateway."
    DEFVAL { disable }
    ::= { bsnAPEntry 25 }

bsnAPNetmask OBJECT-TYPE
      SYNTAX     IpAddress
      MAX-ACCESS read-write
      STATUS     current
      DESCRIPTION
            "The Netmask of the IP address of the AP."
      ::= { bsnAPEntry 26 }

bsnAPGateway OBJECT-TYPE
      SYNTAX     IpAddress
      MAX-ACCESS read-write
      STATUS     current
      DESCRIPTION
            "The Gateway for the AP."
      ::= { bsnAPEntry 27 }

bsnAPStaticIPAddress OBJECT-TYPE
      SYNTAX     IpAddress
      MAX-ACCESS read-write
      STATUS     current
      DESCRIPTION
        "The Static IP-Address configuration for the AP.
         This can only be changed when the LWAPP mode is in Layer-3."
      ::= { bsnAPEntry 28 }

bsnAPBridgingSupport OBJECT-TYPE
      SYNTAX     INTEGER { disable(0), enable(1) }
      MAX-ACCESS read-write
      STATUS     current
      DESCRIPTION
            "This specifies if this AP is a Bridging AP. Bridging APs 
             can be used in Bridging or Mesh network configurations."
      ::= { bsnAPEntry 29 }

bsnAPGroupVlanName OBJECT-TYPE
      SYNTAX     OCTET STRING (SIZE(0..31))
      MAX-ACCESS read-write
      STATUS     current
      DESCRIPTION
       "The AP Group to which this AP has been associated with. 
        If it is empty, then no AP Group overriding has been set."
      ::= { bsnAPEntry 30 }

bsnAPIOSVersion OBJECT-TYPE
    SYNTAX DisplayString
    MAX-ACCESS read-only
    STATUS current
    DESCRIPTION
        "IOS Version of IOS Cisco AP. Zero length string will be 
         returned for other APs"
    ::= {  bsnAPEntry 31 }

bsnAPCertificateType OBJECT-TYPE
    SYNTAX INTEGER { unknown (0), manufactureinstalled (1), 
                     selfsigned(2), localsignificance(3) }
    MAX-ACCESS read-only
    STATUS current
    DESCRIPTION
       "Enum values denoting AP Certificate Type.
        1 : manufactureinstalled : Manufacture Installed Certificate 
            type (MIC).
        2 : selfsigned : Self Signed Certificate type (SSC).
        3 : localsignificance : Local Significance."
    ::= {  bsnAPEntry 32 }

bsnAPEthernetMacAddress OBJECT-TYPE
    SYNTAX MacAddress
    MAX-ACCESS read-only
    STATUS current
    DESCRIPTION
        "The Ethernet MAC address of the AP."
    ::= { bsnAPEntry 33 }
  
bsnAPAdminStatus OBJECT-TYPE
    SYNTAX INTEGER { enable (1), disable (2) }
    MAX-ACCESS read-write
    STATUS current
    DESCRIPTION
        "Admin State of the AP"
    ::= {  bsnAPEntry 37 }

--********************************************************************
-- *  BSN Airespace AP Interface Table
-- *  Rows in this table are created by Airespace Switch as it 
-- *  discovers and associates with the Airespace APEs
--********************************************************************

bsnAPIfTable OBJECT-TYPE
    SYNTAX SEQUENCE OF BsnAPIfEntry
    MAX-ACCESS not-accessible
    STATUS current
    DESCRIPTION
        "Each entry represents an 802.11 interface in an Airespace 
        AP."
    ::= { bsnAP 2 }

bsnAPIfEntry OBJECT-TYPE
    SYNTAX BsnAPIfEntry
    MAX-ACCESS not-accessible
    STATUS current
    DESCRIPTION
        "An entry in bsnAPIfTable."
    INDEX { bsnAPDot3MacAddress, bsnAPIfSlotId }
    ::= { bsnAPIfTable 1 }

BsnAPIfEntry ::=
    SEQUENCE {
        bsnAPIfSlotId                Unsigned32,
        bsnAPIfType                  INTEGER,
        bsnAPIfPhyChannelAssignment  INTEGER,
        bsnAPIfPhyChannelNumber      INTEGER,
        bsnAPIfPhyTxPowerControl     INTEGER,
        bsnAPIfPhyTxPowerLevel       INTEGER,
        bsnAPIfPhyAntennaType        INTEGER,
        bsnAPIfPhyAntennaMode        INTEGER,
        bsnAPIfPhyAntennaDiversity   INTEGER,
        bsnAPIfCellSiteConfigId      Unsigned32,
        bsnAPIfNumberOfVaps          INTEGER,
        bsnAPIfOperStatus            INTEGER,
        bsnAPIfPortNumber            INTEGER,
        bsnAPIfPhyAntennaOptions     INTEGER,
        bsnApIfNoOfUsers             Counter32,
        bsnAPIfWlanOverride          INTEGER,
        bsnAPIfPacketsSniffingFeature INTEGER,
        bsnAPIfSniffChannel          INTEGER,
        bsnAPIfSniffServerIPAddress  IpAddress,
        bsnAPIfAntennaGain           INTEGER,
        bsnAPIfChannelList           DisplayString,
        bsnAPIfAbsolutePowerList     DisplayString,
        bsnAPIfRegulatoryDomainSupport INTEGER,
        bsnAPIfAdminStatus           INTEGER        
    }

bsnAPIfSlotId OBJECT-TYPE
    SYNTAX Unsigned32(0..2)
    MAX-ACCESS read-only
    STATUS current
    DESCRIPTION
        "The slotId of this interface."
    ::= { bsnAPIfEntry 1 }

bsnAPIfType OBJECT-TYPE
    SYNTAX INTEGER { dot11b (1), dot11a (2),uwb (4) }
    MAX-ACCESS read-only
    STATUS current
    DESCRIPTION
        "The type of this interface. dot11b also implies 802.11b/g."
    ::= { bsnAPIfEntry 2 }

bsnAPIfPhyChannelAssignment OBJECT-TYPE
    SYNTAX INTEGER { automatic(1),customized(2)}
    MAX-ACCESS read-write
    STATUS current
    DESCRIPTION
        "If this value is true, then bsnAPDot11CurrentChannel  in
         bsnAPIfDot11PhyDSSSTable is assigned by dynamic
         algorithm and is read-only."
    ::= { bsnAPIfEntry 3 }

bsnAPIfPhyChannelNumber OBJECT-TYPE
     SYNTAX INTEGER { ch1(1),ch2(2),ch3(3),ch4(4),
                      ch5(5),ch6(6),ch7(7),
                      ch8(8),ch9(9),ch10(10),ch11(11),
                      ch12(12),ch13(13),ch14(14),
                      ch34(34),ch36(36),ch38(38),
                      ch40(40),ch42(42),ch44(44),
                      ch46(46),ch48(48),ch52(52),
                      ch56(56),ch60(60),ch64(64),
                      ch100(100),ch104(104),ch108(108),
                      ch112(112),ch116(116),ch120(120),
                      ch124(124),ch128(128),
                      ch132(132),ch136(136),
                      ch140(140),ch149(149),
                      ch153(153),ch157(157),
                      ch161(161),ch165(165),ch169(169)}
     MAX-ACCESS read-write
     STATUS current
     DESCRIPTION
     "Current channel number of the AP Interface.
      Channel numbers will be from 1 to 14 for 802.11b interface type.
      Channel numbers will be from 34 to 169 for 802.11a interface 
      type.  Allowed channel numbers also depends on the current 
      Country Code set in the Switch. This attribute cannot be set 
      unless bsnAPIfPhyChannelAssignment is set to customized else 
      this attribute gets assigned by dynamic algorithm."
    ::= { bsnAPIfEntry 4 }

bsnAPIfPhyTxPowerControl OBJECT-TYPE
    SYNTAX INTEGER { automatic(1),customized(2)}
    MAX-ACCESS read-write
    STATUS current
    DESCRIPTION
        "If this value is true, then bsnAPIfPhyTxPowerLevel
         is assigned by dynamic algorithm and is read-only."
    ::= { bsnAPIfEntry 5 }

bsnAPIfPhyTxPowerLevel OBJECT-TYPE
        SYNTAX INTEGER (1..8)
        MAX-ACCESS read-write
        STATUS current
        DESCRIPTION
           "The TxPowerLevel currently being used to transmit data.
            Some PHYs also use this value to determine the receiver
            sensitivity requirements for CCA. Valid values are between
            1 to 8,depnding on what radio, and this attribute can be 
            set only if bsnAPIfPhyTxPowerControl is set to customized."
    ::= { bsnAPIfEntry 6 }

bsnAPIfPhyAntennaMode OBJECT-TYPE
    SYNTAX INTEGER { sectorA(1),sectorB(2),
                     omni(3),notapplicable(99)}
    MAX-ACCESS read-write
    STATUS current
    DESCRIPTION
    "Antenna Mode of the AP Interface.
     For 802.11a this attribute will always be omni for now.
     This attribute doesn't apply to interface of type 802.11b.
     "
    ::= { bsnAPIfEntry 7 }

bsnAPIfPhyAntennaType OBJECT-TYPE
    SYNTAX INTEGER { internal(1),external(2)}
    MAX-ACCESS read-write
    STATUS current
    DESCRIPTION
    "This attribute specified if the Antenna currently used by AP 
     Radio is internal or external. For 802.11a the antenna is always 
     internal. For 802.11b you can set antenna type to be external or 
     internal."
    ::= { bsnAPIfEntry 8 }

bsnAPIfPhyAntennaDiversity OBJECT-TYPE
     SYNTAX INTEGER { connectorA(0),connectorB(1),
                      enabled(255)}
     MAX-ACCESS read-write
     STATUS current
     DESCRIPTION
    "Diversity doesn't apply to AP Radio of type 802.11a.
     For 802.11b you can set it to connectorA, connectorB or enabled."
    ::= { bsnAPIfEntry 9 }

bsnAPIfCellSiteConfigId OBJECT-TYPE
    SYNTAX Unsigned32
    MAX-ACCESS read-write
    STATUS current
    DESCRIPTION
    "In a cell site configuration, this would be the cell Id of
     this AP Interface"
    ::= { bsnAPIfEntry 10 }

bsnAPIfNumberOfVaps OBJECT-TYPE
    SYNTAX INTEGER(1..16)
    MAX-ACCESS read-only
    STATUS current
    DESCRIPTION
        "Number of WLANs currently active on this AP Interface."
    ::= { bsnAPIfEntry 11 }

bsnAPIfOperStatus OBJECT-TYPE
    SYNTAX INTEGER { down (1), up (2)}
    MAX-ACCESS read-only
    STATUS current    DESCRIPTION
        "Operational status of the interface."
    ::= { bsnAPIfEntry 12 }

bsnAPIfPortNumber OBJECT-TYPE
    SYNTAX INTEGER(0..65535)
    MAX-ACCESS read-only
    STATUS current
    DESCRIPTION
    "Port number on Airespace Switch on which the traffic from this AP
     interface is received."
    ::= {  bsnAPIfEntry 13 }

bsnAPIfPhyAntennaOptions OBJECT-TYPE
    SYNTAX INTEGER { internalAndExternal(0),
                     internal(1),siacAp(2),external(3),
                     ext11bInt11a(4)}
    MAX-ACCESS read-only
    STATUS current
    DESCRIPTION
    "This attribute specifies the Antenna types supported by the AP 
     Radio whether it is internal or external or both. 
     internalAndExternal(0)- internal and external antenna for both 
     11a and 11b
     internal(1) - only internal antenna is allowed.
     siacAp- 11b internal and 11a external
     external - only external antenna is allowed for 11a and 11b
     ext11bInt11a - external antenna for 11b and internal antenna for 
                    11a."
    ::= { bsnAPIfEntry 14 }

bsnApIfNoOfUsers OBJECT-TYPE
        SYNTAX Counter32
        MAX-ACCESS read-only
        STATUS current
        DESCRIPTION
                "No of Users associated with this radio."
        ::= { bsnAPIfEntry 15 }

bsnAPIfWlanOverride  OBJECT-TYPE
    SYNTAX INTEGER { disable(0), enable(1) }
    MAX-ACCESS read-write
    STATUS current    DESCRIPTION
        "This flag when disabled implies that all WLANs are available 
         from this radio.
         However, if this is enabled, then only those WLANs that appear
         in the bsnApIfWlanOverrideTable will be available from this 
         radio."
    ::= { bsnAPIfEntry 16 }

bsnAPIfPacketsSniffingFeature OBJECT-TYPE
    SYNTAX INTEGER { disable(0), enable(1) }
    MAX-ACCESS read-write
    STATUS current    DESCRIPTION
    "This flag when enabled implies that  AP will sniff the 802.11a/bg
     packets.  However, if it is enabled, then user should enter the 
     server-ip-address on which Airopeek is running and the 
     802.11a/bg-channel-number to be sniffed.
     The above feature will work only when AP is in 'Sniffer' mode."
    DEFVAL { disable }
    ::= { bsnAPIfEntry 17 }

bsnAPIfSniffChannel OBJECT-TYPE
     SYNTAX INTEGER { ch0(0),ch1(1),ch2(2),ch3(3),ch4(4),
                      ch5(5),ch6(6),ch7(7),
                      ch8(8),ch9(9),ch10(10),ch11(11),
                      ch12(12),ch13(13),ch14(14),
                      ch34(34),ch36(36),ch38(38),
                      ch40(40),ch42(42),ch44(44),
                      ch46(46),ch48(48),ch52(52),
                      ch56(56),ch60(60),ch64(64),
                      ch100(100),ch104(104),ch108(108),
                      ch112(112),ch116(116),ch120(120),
                      ch124(124),ch128(128),
                      ch132(132),ch136(136),
                      ch140(140),ch149(149),
                      ch153(153),ch157(157),
                      ch161(161),ch165(165),ch169(169)}
     MAX-ACCESS read-write
     STATUS current
     DESCRIPTION
         "This the 802.11a/bg-channel-number on which AP will sniff 
          the packets."
    ::= { bsnAPIfEntry 18 }

bsnAPIfSniffServerIPAddress OBJECT-TYPE
    SYNTAX     IpAddress
    MAX-ACCESS read-write
    STATUS     current
    DESCRIPTION
    "The machine ip address on which Airopeek application is running."
    ::= { bsnAPIfEntry 19 }

bsnAPIfAntennaGain  OBJECT-TYPE
    SYNTAX     INTEGER(0..40)
    MAX-ACCESS read-write
    STATUS     current
    DESCRIPTION
    "Represents antenna gain in multiple of 0.5 dBm. An interger 
     value 4 means 4 x 0.5 = 2 dBm of gain" 
    ::= { bsnAPIfEntry 20 }

bsnAPIfChannelList   OBJECT-TYPE
    SYNTAX     DisplayString
    MAX-ACCESS read-write
    STATUS     current
    DESCRIPTION
    "List of comma separated channels supported by this radio."
    ::= { bsnAPIfEntry 21 }

bsnAPIfAbsolutePowerList     OBJECT-TYPE
    SYNTAX     DisplayString
    MAX-ACCESS read-write
    STATUS     current
    DESCRIPTION
    "List of comma separated absolute power levels supported by this 
    radio."
    ::= { bsnAPIfEntry 22 }

bsnAPIfRegulatoryDomainSupport OBJECT-TYPE
    SYNTAX INTEGER { notSupported(0),
                     supported(1) }
    MAX-ACCESS read-only
    STATUS current
    DESCRIPTION
    "If the regulatory domain on radio is supported or notSupported 
     on the controller"
    ::= { bsnAPIfEntry 23 }

bsnAPIfAdminStatus OBJECT-TYPE
    SYNTAX INTEGER { disable(2), enable(1) }
    MAX-ACCESS read-write
    STATUS current    DESCRIPTION
        "Admin status of the interface."
    ::= { bsnAPIfEntry 34 }

-- *******************************************************************
-- * End of bsnAPIfTable
-- *******************************************************************


--*******************************************************************
-- *  BSN Airespace AP WLAN Override Table
-- *  Rows in this table can be created or deleted by the management
-- *  user of the switch.
--********************************************************************

bsnAPIfWlanOverrideTable OBJECT-TYPE
    SYNTAX SEQUENCE OF BsnAPIfWlanOverrideEntry
    MAX-ACCESS not-accessible
    STATUS current
    DESCRIPTION
        "Each entry represents an SSID added to the AP when the 
         attribute bsnAPIfWlanOverride on the radio is enabled.
         This means only those WLANs on the switch that are added to 
         this table will be available on such a radio."
    ::= { bsnAP 21 }

bsnAPIfWlanOverrideEntry OBJECT-TYPE
    SYNTAX BsnAPIfWlanOverrideEntry
    MAX-ACCESS not-accessible
    STATUS current
    DESCRIPTION
        "An entry in bsnAPIfWlanOverrideTable"
    INDEX { bsnAPDot3MacAddress, bsnAPIfSlotId, 
            bsnAPIfWlanOverrideId }
    ::= { bsnAPIfWlanOverrideTable 1 }

BsnAPIfWlanOverrideEntry ::=
    SEQUENCE {
    bsnAPIfWlanOverrideId               Unsigned32,
    bsnAPIfWlanOverrideSsid             DisplayString,
    bsnAPIfWlanOverrideRowStatus        RowStatus
    }

bsnAPIfWlanOverrideId OBJECT-TYPE
        SYNTAX Unsigned32(1..16)
        MAX-ACCESS read-create
        STATUS current
        DESCRIPTION
           "Index of the WLAN (bsnDot11EssIndex) added to the radio.
            Airespace Switch supports 16 Airespace WLANs so index
            will be from 1 to 16."
    ::= { bsnAPIfWlanOverrideEntry 1 }

bsnAPIfWlanOverrideSsid OBJECT-TYPE
        SYNTAX DisplayString (SIZE(1..32))
        MAX-ACCESS read-only
        STATUS current
        DESCRIPTION
             "SSID assigned to the override WLAN."
    ::= { bsnAPIfWlanOverrideEntry 2 }

bsnAPIfWlanOverrideRowStatus OBJECT-TYPE
        SYNTAX RowStatus
        MAX-ACCESS read-create
        STATUS current
        DESCRIPTION
                "A row status type for the bsnAPIfWlanOverrideEntry"
    ::= { bsnAPIfWlanOverrideEntry 15 }

--*******************************************************************
-- *  BSN Airespace AP Smt Param Table
-- *  Rows in this table are created by Airespace Switch as it 
-- *  discovers and associates with the Airespace APs
--********************************************************************

bsnAPIfSmtParamTable OBJECT-TYPE
    SYNTAX SEQUENCE OF BsnAPIfSmtParamEntry
    MAX-ACCESS not-accessible
    STATUS current
    DESCRIPTION
        "Each entry represents SMT parameters on an 802.11 interface 
         of an Airespace AP."
    ::= { bsnAP 3 }

bsnAPIfSmtParamEntry OBJECT-TYPE
    SYNTAX BsnAPIfSmtParamEntry
    MAX-ACCESS not-accessible
    STATUS current
    DESCRIPTION
        "An entry in bsnAPIfSmtParamTable"
    INDEX { bsnAPDot3MacAddress, bsnAPIfSlotId }
    ::= { bsnAPIfSmtParamTable 1 }

BsnAPIfSmtParamEntry ::=
    SEQUENCE {
    bsnAPIfDot11BeaconPeriod                      INTEGER,
    bsnAPIfDot11MediumOccupancyLimit              INTEGER,
    bsnAPIfDot11CFPPeriod                         INTEGER,
    bsnAPIfDot11CFPMaxDuration                    INTEGER,
    bsnAPIfDot11OperationalRateSet                OCTET STRING,
    bsnAPIfDot11DTIMPeriod                        INTEGER,
    bsnAPIfDot11MultiDomainCapabilityImplemented  INTEGER,
    bsnAPIfDot11MultiDomainCapabilityEnabled      INTEGER,
    bsnAPIfDot11CountryString                     OCTET STRING,
    bsnAPIfDot11SmtParamsConfigType               INTEGER,
    bsnAPIfDot11BSSID                             MacAddress
    }
bsnAPIfDot11BeaconPeriod OBJECT-TYPE
    SYNTAX INTEGER (20..1000)
    MAX-ACCESS read-only
    STATUS current
    DESCRIPTION
        "This attribute shall specify the number of TU that a
         AP Interface shall use for scheduling Beacon tranmissions.
         This value is transmitted in Beacon and Probe Response
         frames."
   ::= {bsnAPIfSmtParamEntry 1}

bsnAPIfDot11MediumOccupancyLimit OBJECT-TYPE
    SYNTAX INTEGER (0..1000)
    MAX-ACCESS read-only
    STATUS current
    DESCRIPTION
        "This attribute shall indicate the maximum amount of time,
         in TU, that a point coordinator may control the usage of
         the wireless medium without relinquishing control for long
         enough to allow at least one instance of DCF access to the
         medium.  The default value of this attribute shall be 100,
         and the maximum value shall be 1000."
    ::= { bsnAPIfSmtParamEntry 2 }

bsnAPIfDot11CFPPeriod OBJECT-TYPE
    SYNTAX INTEGER (0..255)
    MAX-ACCESS read-only
    STATUS current
    DESCRIPTION
        "The attribute shall describe the number of DTIM intervals
         between the start of CFPs.  It is modified by
         MLME-START.request primitive."
    ::= { bsnAPIfSmtParamEntry 3 }

bsnAPIfDot11CFPMaxDuration OBJECT-TYPE
    SYNTAX INTEGER (0..65535)
    MAX-ACCESS read-only
    STATUS current
    DESCRIPTION
        "The attribute shall describe the maximum duration of the CFP
         in TU that may be generated by the PCF. It is modified by
         MLME-START.request primitive."
    ::= { bsnAPIfSmtParamEntry 4 }


bsnAPIfDot11OperationalRateSet OBJECT-TYPE
     SYNTAX OCTET STRING (SIZE(1..126))
     MAX-ACCESS read-only
     STATUS current
     DESCRIPTION
            "This attribute shall specify the set of data rates
             at which the AP Interface may transmit data.  Each octet
             contains a value representing a rate.  Each rate
             shall be within the range from 2 to 127,
             corresponding to data rates in increments of
             500 kb/s from 1 Mb/s to 63.5 Mb/s, and shall be
             supported (as indicated in the supported rates
             table) for receiving data. This value is reported in
             transmitted Beacon, Probe Request, Probe Response,
             Association Request, Association Response,
             Reassociation Request, and Reassociation Response
             frames, and is used to determine whether a BSS
             with which the AP Interface desires to synchronize is
             suitable. It is also used when starting a BSS,
             as specified in  10.3."
    ::= { bsnAPIfSmtParamEntry 5 }

bsnAPIfDot11DTIMPeriod OBJECT-TYPE
        SYNTAX INTEGER(1..255)
        MAX-ACCESS read-only
        STATUS current
        DESCRIPTION
               "This attribute shall specify the number of beacon
                intervals that shall elapse between transmission of
                Beacons frames containing a TIM element whose DTIM
                Count field is 0. This value is transmitted in
                the DTIM Period field of Beacon frames."
        ::= { bsnAPIfSmtParamEntry 6 }

bsnAPIfDot11MultiDomainCapabilityImplemented OBJECT-TYPE
         SYNTAX INTEGER { notimplemented(0),implemented(1)}
         MAX-ACCESS read-only
         STATUS current
         DESCRIPTION
                "This attribute, when TRUE, indicates that the
                 AP Interface implementation is capable of supporting
                 multiple regulatory domains.  The capability is
                 disabled, otherwise.  The default value of this
                 attribute is FALSE."
        ::= { bsnAPIfSmtParamEntry 7 }

bsnAPIfDot11MultiDomainCapabilityEnabled OBJECT-TYPE
                SYNTAX INTEGER { no(0),yes(1)}
                MAX-ACCESS read-only
                STATUS current
                DESCRIPTION
                       "This attribute, when TRUE, indicates that the
                        capability of the AP Interface to operate in 
                        multiple regulatory domains is enabled.  The 
                        capability is disabled, otherwise.  The default
                        value of this attribute is FALSE."
        ::= { bsnAPIfSmtParamEntry 8 }

bsnAPIfDot11CountryString OBJECT-TYPE
        SYNTAX OCTET STRING (SIZE(3))
        MAX-ACCESS read-only
        STATUS current
        DESCRIPTION
                "This attribute identifies the country in which the
                AP Interface is operating. The first two octets of 
                this string is the two character country code as 
                described in document ISO/IEC 3166-1.  The third octet
                shall be one of the following:

                1. an ASCII space character, if the regulations under
                which the AP Interface is operating encompass all
                environments in the country,

                2. an ASCII 'O' character, if the regulations under
                which the AP Interface is operating are for an Outdoor
                environment only, or

                3. an ASCII 'I' character, if the regulations under
                which the AP Interface is operating are for an Indoor
                environment only."
        ::= { bsnAPIfSmtParamEntry 9 }

bsnAPIfDot11SmtParamsConfigType OBJECT-TYPE
        SYNTAX INTEGER { automatic(0),customized(1)}
        MAX-ACCESS read-only
        STATUS current
        DESCRIPTION
                "This attribute suggests if the Station parameters for
                 this radio are automatically set or have been 
                 customized."
    ::= { bsnAPIfSmtParamEntry 10 }

bsnAPIfDot11BSSID OBJECT-TYPE
    SYNTAX MacAddress
    MAX-ACCESS read-only
    STATUS current
    DESCRIPTION
        "BSSID of this AP config which would be the MAC Address of AP"
    ::= { bsnAPIfSmtParamEntry 30 }

--********************************************************************
-- *  bsnAPIfMultiDomainCapabilityTable
--********************************************************************

bsnAPIfMultiDomainCapabilityTable OBJECT-TYPE
    SYNTAX SEQUENCE OF BsnAPIfMultiDomainCapabilityEntry
    MAX-ACCESS not-accessible
    STATUS current
    DESCRIPTION
        "Each entry represents an 803.2 or an 802.11 interface in an 
         Airespace AP."
    ::= { bsnAP 4 }

bsnAPIfMultiDomainCapabilityEntry OBJECT-TYPE
    SYNTAX BsnAPIfMultiDomainCapabilityEntry
    MAX-ACCESS not-accessible
    STATUS current
    DESCRIPTION
        "Each entry represents an 803.2 or an 802.11 interface in an 
         Airespace AP."
    INDEX { bsnAPDot3MacAddress, bsnAPIfSlotId }
    ::= { bsnAPIfMultiDomainCapabilityTable 1 }

BsnAPIfMultiDomainCapabilityEntry ::=
    SEQUENCE {
    bsnAPIfDot11MaximumTransmitPowerLevel        Integer32,
    bsnAPIfDot11FirstChannelNumber               Integer32,
    bsnAPIfDot11NumberofChannels                 Integer32
    }

bsnAPIfDot11MaximumTransmitPowerLevel OBJECT-TYPE
        SYNTAX Integer32
        MAX-ACCESS read-only
        STATUS current
        DESCRIPTION
            "This attribute shall indicate the maximum transmit power, 
             in dBm, allowed in the subband for the associated domain 
             country string. The default value of this attribute shall
             be zero."
        ::= { bsnAPIfMultiDomainCapabilityEntry 1 }

bsnAPIfDot11FirstChannelNumber OBJECT-TYPE
        SYNTAX Integer32
        MAX-ACCESS read-only
        STATUS current
        DESCRIPTION
            "This attribute shall indicate the value of the lowest 
             channel number in the subband for the associated domain 
             country string. The default value of this attribute shall
             be zero."
        ::= { bsnAPIfMultiDomainCapabilityEntry 2 }

bsnAPIfDot11NumberofChannels OBJECT-TYPE
        SYNTAX Integer32
        MAX-ACCESS read-only
        STATUS current
        DESCRIPTION
              "This attribute shall indicate the value of the total 
               number of channels allowed in the subband for the 
               associated domain country string. The default value 
               of this attribute shall be zero."
        ::= { bsnAPIfMultiDomainCapabilityEntry 20 }


--********************************************************************
-- *    bsnDot11MacOperationTable  
--********************************************************************

bsnAPIfMacOperationParamTable OBJECT-TYPE
        SYNTAX SEQUENCE OF BsnAPIfMacOperationParamEntry
        MAX-ACCESS not-accessible
        STATUS current
        DESCRIPTION
           "Group contains MAC attributes pertaining to the operation
            of the MAC. These would be read only attributes as they 
            would be updated by RRM Dynamic Algorithm. If user needs 
            to configure them then they can only be configured 
            globally"
    ::= { bsnAP 5 }

bsnAPIfMacOperationParamEntry OBJECT-TYPE
        SYNTAX BsnAPIfMacOperationParamEntry
        MAX-ACCESS not-accessible
        STATUS current
        DESCRIPTION
           "An entry in the bsnAPIfMacOperationParamEntry Table.
            Interface tables in this MIB module are indexed
            by bsnAPDot3MacAddress, bsnAPIfSlotId."
        INDEX { bsnAPDot3MacAddress, bsnAPIfSlotId }
    ::= { bsnAPIfMacOperationParamTable 1 }

BsnAPIfMacOperationParamEntry ::=
        SEQUENCE {
                 bsnAPIfDot11MacRTSThreshold             INTEGER,
                 bsnAPIfDot11MacShortRetryLimit          INTEGER,
                 bsnAPIfDot11MacLongRetryLimit           INTEGER,
                 bsnAPIfDot11MacFragmentationThreshold   INTEGER,
                 bsnAPIfDot11MacMaxTransmitMSDULifetime  Unsigned32,
                 bsnAPIfDot11MacParamsConfigType         INTEGER,
                 bsnAPIfDot11MacMaxReceiveLifetime       Unsigned32
               }


bsnAPIfDot11MacRTSThreshold OBJECT-TYPE
        SYNTAX INTEGER (0..2347)
        MAX-ACCESS read-only
        STATUS current
        DESCRIPTION
                "If bsnAPIfMacParamsAutomaticOn is true then this is 
                 read only parameter updated by RRM dynamic algorithm"
    ::= { bsnAPIfMacOperationParamEntry 1 }

bsnAPIfDot11MacShortRetryLimit OBJECT-TYPE
        SYNTAX INTEGER (1..255)
        MAX-ACCESS read-only
        STATUS current
        DESCRIPTION
                "If bsnAPIfMacParamsAutomaticOn is true then this is
                read only parameter updated by RRM dynamic algorithm"
    ::= { bsnAPIfMacOperationParamEntry 2 }

bsnAPIfDot11MacLongRetryLimit OBJECT-TYPE
        SYNTAX INTEGER (1..255)
        MAX-ACCESS read-only
        STATUS current
        DESCRIPTION
                "If bsnAPIfMacParamsAutomaticOn is true then this is
                read only parameter updated by RRM dynamic algorithm"
    ::= { bsnAPIfMacOperationParamEntry 3 }

bsnAPIfDot11MacFragmentationThreshold OBJECT-TYPE
        SYNTAX INTEGER (256..2346)
        MAX-ACCESS read-only
        STATUS current
        DESCRIPTION
                "If bsnAPIfMacParamsAutomaticOn is true then this is
                read only parameter updated by RRM dynamic algorithm "
    ::= { bsnAPIfMacOperationParamEntry 4 }

bsnAPIfDot11MacMaxTransmitMSDULifetime OBJECT-TYPE
        SYNTAX Unsigned32 (1..4294967295)
        MAX-ACCESS read-only
        STATUS current
        DESCRIPTION
                "If bsnAPIfMacParamsAutomaticOn is true then this is
                read only parameter updated by RRM dynamic algorithm"
    ::= { bsnAPIfMacOperationParamEntry 5 }

bsnAPIfDot11MacParamsConfigType OBJECT-TYPE
        SYNTAX INTEGER { automatic(0),customized(1)}
        MAX-ACCESS read-only
        STATUS current
        DESCRIPTION
                "This attribute suggests if the MAC parameters for this
                 radio are automatically set or have been customized."
    ::= { bsnAPIfMacOperationParamEntry 6 }

bsnAPIfDot11MacMaxReceiveLifetime OBJECT-TYPE
        SYNTAX Unsigned32 (1..4294967295)
        MAX-ACCESS read-only
        STATUS current
        DESCRIPTION
            "If bsnAPIfMacParamsAutomaticOn is true then this is
            read only parameter updated by RRM dynamic algorithm"
    ::= { bsnAPIfMacOperationParamEntry 25 }

-- *******************************************************************
-- * Begin of bsnAPIfDot11CountersTable
-- *******************************************************************

bsnAPIfDot11CountersTable OBJECT-TYPE
    SYNTAX SEQUENCE OF BsnAPIfDot11CountersEntry
    MAX-ACCESS not-accessible
    STATUS current
    DESCRIPTION
        "Group containing attributes that are MAC counters.
        Each instance represents counters on a AP dot11 interface"
        ::= { bsnAP 6 }
bsnAPIfDot11CountersEntry OBJECT-TYPE
    SYNTAX BsnAPIfDot11CountersEntry
    MAX-ACCESS not-accessible
    STATUS current
    DESCRIPTION
        "An entry in the dot11CountersEntry Table.
         Interface tables in this MIB module are indexed
         by bsnAPDot3MacAddress and bsnAPIfSlotId"
    INDEX { bsnAPDot3MacAddress, bsnAPIfSlotId }
    ::= { bsnAPIfDot11CountersTable 1 }

BsnAPIfDot11CountersEntry ::=
        SEQUENCE {
                bsnAPIfDot11TransmittedFragmentCount       Counter32,
                bsnAPIfDot11MulticastTransmittedFrameCount Counter32,
                bsnAPIfDot11RetryCount                     Counter32,
                bsnAPIfDot11MultipleRetryCount             Counter32,
                bsnAPIfDot11FrameDuplicateCount            Counter32,
                bsnAPIfDot11RTSSuccessCount                Counter32,
                bsnAPIfDot11RTSFailureCount                Counter32,
                bsnAPIfDot11ACKFailureCount                Counter32,
                bsnAPIfDot11ReceivedFragmentCount          Counter32,
                bsnAPIfDot11MulticastReceivedFrameCount    Counter32,
                bsnAPIfDot11FCSErrorCount                  Counter32,
                bsnAPIfDot11TransmittedFrameCount          Counter32,
                bsnAPIfDot11WEPUndecryptableCount          Counter32,
                bsnAPIfDot11FailedCount                    Counter32}

bsnAPIfDot11TransmittedFragmentCount OBJECT-TYPE
    SYNTAX Counter32
    MAX-ACCESS read-only
    STATUS current
    DESCRIPTION
        "This counter shall be incremented for an acknowledged MPDU
        with an individual address in the address 1 field or an MPDU
        with a multicast address in the address 1 field of type Data
        or Management."
    ::= { bsnAPIfDot11CountersEntry 1 }

bsnAPIfDot11MulticastTransmittedFrameCount OBJECT-TYPE
    SYNTAX Counter32
    MAX-ACCESS read-only
    STATUS current
    DESCRIPTION
        "This counter shall increment only when the multicast bit
        is set in the destination MAC address of a successfully
        transmitted MSDU.  When operating as a STA in an ESS, where
        these frames are directed to the AP, this implies having
        received an acknowledgment to all associated MPDUs."
    ::= { bsnAPIfDot11CountersEntry 2 }

bsnAPIfDot11RetryCount OBJECT-TYPE
    SYNTAX Counter32
    MAX-ACCESS read-only
    STATUS current
    DESCRIPTION
        "This counter shall increment when an MSDU is successfully
        transmitted after one or more retransmissions."
    ::= { bsnAPIfDot11CountersEntry 3 }

bsnAPIfDot11MultipleRetryCount OBJECT-TYPE
    SYNTAX Counter32
    MAX-ACCESS read-only
    STATUS current
    DESCRIPTION
        "This counter shall increment when an MSDU is successfully
       transmitted after more than one retransmission."
    ::= { bsnAPIfDot11CountersEntry 4 }

bsnAPIfDot11FrameDuplicateCount  OBJECT-TYPE
  SYNTAX Counter32
  MAX-ACCESS read-only
    STATUS current
    DESCRIPTION
          "This counter shall increment when a frame is received
          that the Sequence Control field indicates is a
        duplicate."
    ::= { bsnAPIfDot11CountersEntry 5 }

bsnAPIfDot11RTSSuccessCount OBJECT-TYPE
        SYNTAX Counter32
        MAX-ACCESS read-only
        STATUS current
        DESCRIPTION
            "This counter shall increment when a CTS is received in
            response to an RTS."
    ::= {  bsnAPIfDot11CountersEntry 6 }

bsnAPIfDot11RTSFailureCount OBJECT-TYPE
        SYNTAX Counter32
        MAX-ACCESS read-only
        STATUS current
        DESCRIPTION
            "This counter shall increment when a CTS is not received in
            response to an RTS."
    ::= { bsnAPIfDot11CountersEntry 7 }

bsnAPIfDot11ACKFailureCount OBJECT-TYPE
        SYNTAX Counter32
        MAX-ACCESS read-only
        STATUS current
        DESCRIPTION
            "This counter shall increment when an ACK is not received
            when expected."
    ::= {  bsnAPIfDot11CountersEntry 8 }

bsnAPIfDot11ReceivedFragmentCount OBJECT-TYPE
        SYNTAX Counter32
        MAX-ACCESS read-only
        STATUS current
        DESCRIPTION
            "This counter shall be incremented for each successfully
            received MPDU of type Data or Management."
    ::= { bsnAPIfDot11CountersEntry 9 }

bsnAPIfDot11MulticastReceivedFrameCount OBJECT-TYPE
        SYNTAX Counter32
        MAX-ACCESS read-only
        STATUS current
        DESCRIPTION
            "This counter shall increment when a MSDU is received
            with the multicast bit set in the destination
            MAC address."
    ::= { bsnAPIfDot11CountersEntry 10 }

bsnAPIfDot11FCSErrorCount OBJECT-TYPE
        SYNTAX Counter32
        MAX-ACCESS read-only
        STATUS current
        DESCRIPTION
            "This counter shall increment when an FCS error is
            detected in a received MPDU."
    ::= { bsnAPIfDot11CountersEntry 11 }

bsnAPIfDot11TransmittedFrameCount OBJECT-TYPE
        SYNTAX Counter32
        MAX-ACCESS read-only
        STATUS current
        DESCRIPTION
        "This counter shall increment for each successfully
                transmitted MSDU."
    ::= { bsnAPIfDot11CountersEntry 12 }

bsnAPIfDot11WEPUndecryptableCount OBJECT-TYPE
        SYNTAX Counter32
        MAX-ACCESS read-only
        STATUS current
        DESCRIPTION
         "This counter shall increment when a frame is received with
         the WEP subfield of the Frame Control field set to one and the
         WEPOn value for the key mapped to the TA's MAC address
         indicates that the frame should not have been encrypted or
         that frame is discarded due to the receiving STA not
         implementing the privacy option."
    ::= { bsnAPIfDot11CountersEntry 13 }


bsnAPIfDot11FailedCount OBJECT-TYPE
    SYNTAX Counter32
    MAX-ACCESS read-only
    STATUS current
    DESCRIPTION
         "This counter shall increment when an MSDU is not transmitted
          successfully due to the number of transmit attempts exceeding
          either the  bsnAPIfDot11ShortRetryLimit or dot11LongRetryLimit."
    ::= { bsnAPIfDot11CountersEntry 33 }

-- *******************************************************************
-- * End of bsnAPIfCountersTable
-- *******************************************************************


-- **********************************************************************
-- *    bsnAPIfDot11PhyTxPower  TABLE
-- **********************************************************************

bsnAPIfDot11PhyTxPowerTable OBJECT-TYPE
        SYNTAX SEQUENCE OF BsnAPIfDot11PhyTxPowerEntry
        MAX-ACCESS not-accessible
        STATUS deprecated
        DESCRIPTION
            "Group of attributes for bsnAPIfDot11PhyTxPowerTable.
            Implemented as a table indexed on STA ID to allow for 
            multiple instances on an Agent. This table has been
            deprecated. The level and power can be obtained from
            bsnAPIfTable(bsnAPIfAbsolutePowerList)."
    ::= { bsnAP 8}

bsnAPIfDot11PhyTxPowerEntry OBJECT-TYPE
        SYNTAX BsnAPIfDot11PhyTxPowerEntry
        MAX-ACCESS not-accessible
        STATUS deprecated
        DESCRIPTION
            "An entry in the bsnAPIfDot11PhyTxPower Table.
            Interface tables in this MIB module are indexed
            by bsnAPDot3MacAddress, bsnAPIfSlotId."
        INDEX { bsnAPDot3MacAddress, bsnAPIfSlotId }
    ::= { bsnAPIfDot11PhyTxPowerTable 1 }

BsnAPIfDot11PhyTxPowerEntry ::=
        SEQUENCE {
                bsnAPIfDot11NumberSupportedPowerLevels  INTEGER,
                bsnAPIfDot11TxPowerLevel1               INTEGER,
                bsnAPIfDot11TxPowerLevel2               INTEGER,
                bsnAPIfDot11TxPowerLevel3               INTEGER,
                bsnAPIfDot11TxPowerLevel4               INTEGER,
                bsnAPIfDot11TxPowerLevel5               INTEGER,
                bsnAPIfDot11TxPowerLevel6               INTEGER,
                bsnAPIfDot11TxPowerLevel7               INTEGER,
                bsnAPIfDot11TxPowerLevel8               INTEGER }


bsnAPIfDot11NumberSupportedPowerLevels OBJECT-TYPE
        SYNTAX INTEGER (1..8)
        MAX-ACCESS read-only
        STATUS deprecated
        DESCRIPTION
            "The number of power levels supported by the PMD.
            This attribute can have a value of 1 to 8."
    ::= { bsnAPIfDot11PhyTxPowerEntry 1 }

bsnAPIfDot11TxPowerLevel1 OBJECT-TYPE
        SYNTAX INTEGER (0..10000)
        MAX-ACCESS read-only
        STATUS deprecated
        DESCRIPTION
            "The transmit output power for LEVEL1 in mW.
            This is also the default power level. It is same as the 
            Maximum power level available on an AP interface."
    ::= { bsnAPIfDot11PhyTxPowerEntry 2 }

bsnAPIfDot11TxPowerLevel2 OBJECT-TYPE
        SYNTAX INTEGER (0..10000)
        MAX-ACCESS read-only
        STATUS deprecated
        DESCRIPTION
            "The transmit output power for LEVEL2 in mW. It is 1/2 of 
             the Maximum power level available on an AP interface."
    ::= { bsnAPIfDot11PhyTxPowerEntry 3 }

bsnAPIfDot11TxPowerLevel3 OBJECT-TYPE
        SYNTAX INTEGER (0..10000)
        MAX-ACCESS read-only
        STATUS deprecated
        DESCRIPTION
            "The transmit output power for LEVEL3 in mW. It is 1/4th 
             of the Maximum power level available on an AP interface."
    ::= { bsnAPIfDot11PhyTxPowerEntry 4 }

bsnAPIfDot11TxPowerLevel4 OBJECT-TYPE
        SYNTAX INTEGER (0..10000)
        MAX-ACCESS read-only
        STATUS deprecated
        DESCRIPTION
            "The transmit output power for LEVEL4 in mW. It is 1/8th of
             the Maximum power level available on an AP interface."
    ::= { bsnAPIfDot11PhyTxPowerEntry 5 }

bsnAPIfDot11TxPowerLevel5 OBJECT-TYPE
        SYNTAX INTEGER (0..10000)
        MAX-ACCESS read-only
        STATUS deprecated
        DESCRIPTION
            "The transmit output power for LEVEL5 in mW. It is 1/16th 
             of the Maximum power level available on an AP interface."
    ::= { bsnAPIfDot11PhyTxPowerEntry 6 }

bsnAPIfDot11TxPowerLevel6 OBJECT-TYPE
        SYNTAX INTEGER (0..10000)
        MAX-ACCESS read-only
        STATUS deprecated
        DESCRIPTION
            "The transmit output power for LEVEL6 in mW. It is 1/32th 
             of the Maximum power level available on an AP interface."
    ::= { bsnAPIfDot11PhyTxPowerEntry 7 }

bsnAPIfDot11TxPowerLevel7 OBJECT-TYPE
        SYNTAX INTEGER (0..10000)
        MAX-ACCESS read-only
        STATUS deprecated
        DESCRIPTION
            "The transmit output power for LEVEL7 in mW. It is 1/64th 
             of the Maximum power level available on an AP interface."
    ::= { bsnAPIfDot11PhyTxPowerEntry 8 }

bsnAPIfDot11TxPowerLevel8 OBJECT-TYPE
        SYNTAX INTEGER (0..10000)
        MAX-ACCESS read-only
        STATUS deprecated
        DESCRIPTION
            "The transmit output power for LEVEL8 in mW. It is 1/128th
             of the Maximum power level available on an AP interface."
    ::= { bsnAPIfDot11PhyTxPowerEntry 28 }


-- ********************************************************************
-- *    End of bsnAPIfDot11PhyTxPowerTable
-- ********************************************************************


-- ********************************************************************
-- *    bsnAPIfDot11PhyChannelTable  
-- ********************************************************************

bsnAPIfDot11PhyChannelTable OBJECT-TYPE
        SYNTAX SEQUENCE OF BsnAPIfDot11PhyChannelEntry
        MAX-ACCESS not-accessible
        STATUS current
        DESCRIPTION
            "Entry of attributes for bsnAPIfDot11PhyChannelEntry.
            Implemented as a table indexed on bsnAPDot3MacAddress,
            bsnAPIfSlotId allow for multiple instances on an Agent"
    ::= { bsnAP 9 }

bsnAPIfDot11PhyChannelEntry OBJECT-TYPE
        SYNTAX BsnAPIfDot11PhyChannelEntry
        MAX-ACCESS not-accessible
        STATUS current
        DESCRIPTION
            "An entry in the bsnAPIfDot11PhyChannelEntry Table.
             Interface tables in this MIB module are indexed
            by bsnAPDot3MacAddress, bsnAPIfSlotId."
        INDEX { bsnAPDot3MacAddress, bsnAPIfSlotId }
    ::= { bsnAPIfDot11PhyChannelTable 1 }

BsnAPIfDot11PhyChannelEntry ::=
        SEQUENCE {
                        bsnAPIfDot11CurrentCCAMode    INTEGER,
                        bsnAPIfDot11EDThreshold       Integer32,
                        bsnAPIfDot11TIThreshold       Integer32 }

bsnAPIfDot11CurrentCCAMode OBJECT-TYPE
        SYNTAX INTEGER { edonly(1), csonly(2),
                         edandcs(4), cswithtimer(8),
                         hrcsanded(16) }
        MAX-ACCESS read-only
        STATUS current
        DESCRIPTION
            "The current CCA method in operation.Valid values are:
                energy detect only (edonly) = 01,
                carrier sense only (csonly) = 02,
                carrier sense and energy detect (edandcs)= 04
                carrier sense with timer (cswithtimer)= 08
                high rate carrier sense and energy detect 
                (hrcsanded)=16."
    ::= { bsnAPIfDot11PhyChannelEntry 1 }

bsnAPIfDot11EDThreshold OBJECT-TYPE
        SYNTAX Integer32
        MAX-ACCESS read-only
        STATUS current
        DESCRIPTION
            "The current Energy Detect Threshold being used by the 
             Channel PHY."
    ::= { bsnAPIfDot11PhyChannelEntry 2 }

bsnAPIfDot11TIThreshold OBJECT-TYPE
    SYNTAX Integer32
    MAX-ACCESS read-only
    STATUS current
    DESCRIPTION
        "The Threshold being used to detect a busy medium (frequency).
        CCA shall report a busy medium upon detecting the RSSI above 
        this threshold."
    ::= { bsnAPIfDot11PhyChannelEntry 23 }

--********************************************************************
-- *    End of bsnAPIfDot11PhyDSSSTable
--********************************************************************


--********************************************************************
-- * Begin of bsnAPIfProfileThresholdConfigTable  
--********************************************************************

bsnAPIfProfileThresholdConfigTable OBJECT-TYPE
          SYNTAX SEQUENCE OF BsnAPIfProfileThresholdConfigEntry
          MAX-ACCESS not-accessible
          STATUS current
          DESCRIPTION
                  "Table of attributes for various thresholds to be
                  set on each Airespace AP Interface for Load 
                  performance profile , interference performance 
                  profile and Noise performance profile."
          ::= { bsnAP 12 }

bsnAPIfProfileThresholdConfigEntry OBJECT-TYPE
        SYNTAX BsnAPIfProfileThresholdConfigEntry
        MAX-ACCESS not-accessible
        STATUS current
        DESCRIPTION
                "An entry (conceptual row) in the Phy Thresholds 
                Table. Entries in this MIB are indexed by 
                bsnAPDot3MacAddress and bsnAPIfSlotId"
        INDEX { bsnAPDot3MacAddress, bsnAPIfSlotId}
    ::= { bsnAPIfProfileThresholdConfigTable 1 }

BsnAPIfProfileThresholdConfigEntry ::=
                SEQUENCE {
            bsnAPIfProfileParamAssignment       INTEGER,
            bsnAPIfForeignInterferenceThreshold INTEGER,
            bsnAPIfForeignNoiseThreshold        INTEGER,
            bsnAPIfRFUtilizationThreshold       INTEGER,
            bsnAPIfThroughputThreshold          Unsigned32,
            bsnAPIfMobilesThreshold             INTEGER,
            bsnAPIfCoverageThreshold            INTEGER,
            bsnAPIfMobileMinExceptionLevel      INTEGER,
            bsnAPIfCoverageExceptionLevel       INTEGER
                }

bsnAPIfProfileParamAssignment OBJECT-TYPE
    SYNTAX INTEGER { automatic(1),customized(2)}
    MAX-ACCESS read-write
    STATUS current
    DESCRIPTION
    "If this value is automatic then Profile Parameters in 
     bsnRrmDot11aAPProfile at the global level will be used.
     If this value is customized then Profile Parameters in 
     bsnAPIfProfileThresholdConfig
     Table will be used and user can customize them per AP."
    ::= { bsnAPIfProfileThresholdConfigEntry 1 }


bsnAPIfForeignInterferenceThreshold OBJECT-TYPE
    SYNTAX INTEGER(0..100)
    MAX-ACCESS read-write
    STATUS current
    DESCRIPTION
      "foreign interference threshold between 0 and 100 percent."
   ::= {bsnAPIfProfileThresholdConfigEntry 2 }

bsnAPIfForeignNoiseThreshold OBJECT-TYPE
    SYNTAX INTEGER(-127..0)
    MAX-ACCESS read-write
    STATUS current
    DESCRIPTION
     "foreign noise threshold between -100 and -50 dBm."
   ::= {bsnAPIfProfileThresholdConfigEntry 3 }

bsnAPIfRFUtilizationThreshold OBJECT-TYPE
    SYNTAX INTEGER(0..100)
    MAX-ACCESS read-write
    STATUS current
    DESCRIPTION
    "RF utlization threshold between 0 and 100 percent."
   ::= {bsnAPIfProfileThresholdConfigEntry 4 }

bsnAPIfThroughputThreshold OBJECT-TYPE
    SYNTAX Unsigned32(1000..1000000)
    MAX-ACCESS read-write
    STATUS current
    DESCRIPTION
    " Airespace AP data-rate threshold between 1000 and 100000"
   ::= {bsnAPIfProfileThresholdConfigEntry 5 }

bsnAPIfMobilesThreshold OBJECT-TYPE
    SYNTAX INTEGER(1..75)
    MAX-ACCESS read-write
    STATUS current
    DESCRIPTION
    " Airespace AP mobiles threshold between 1 and 75"
   ::= {bsnAPIfProfileThresholdConfigEntry 6 }

bsnAPIfCoverageThreshold OBJECT-TYPE
    SYNTAX INTEGER(3..50)
    MAX-ACCESS read-write
    STATUS current
    DESCRIPTION
    "  Airespace AP coverage threshold between 3 and 50"
   ::= {bsnAPIfProfileThresholdConfigEntry 7 }

bsnAPIfMobileMinExceptionLevel OBJECT-TYPE
    SYNTAX INTEGER(1..75)
    MAX-ACCESS read-write
    STATUS current
    DESCRIPTION
    "  Airespace AP mobile minimum exception level between 1 and 1000"
   ::= {bsnAPIfProfileThresholdConfigEntry 8 }

bsnAPIfCoverageExceptionLevel OBJECT-TYPE
    SYNTAX INTEGER(0..100)
    MAX-ACCESS read-write
    STATUS current
    DESCRIPTION
    "Airespace AP coverage exception level between 0 and 100 percent."
   ::= {bsnAPIfProfileThresholdConfigEntry 28 }

--********************************************************************
-- * End of bsnAPIfProfileThresholdConfigTable
--********************************************************************

--********************************************************************
-- * Begin of bsnAPIfLoadParametersTable
--********************************************************************
bsnAPIfLoadParametersTable OBJECT-TYPE
        SYNTAX SEQUENCE OF BsnAPIfLoadParametersEntry
        MAX-ACCESS not-accessible
        STATUS current
        DESCRIPTION
                "These are RRM performance related read only parameters
                 per Airespace AP"
        ::= { bsnAP 13 }

bsnAPIfLoadParametersEntry OBJECT-TYPE
        SYNTAX BsnAPIfLoadParametersEntry
        MAX-ACCESS not-accessible
        STATUS current
        DESCRIPTION
                "An entry (conceptual row) in the Table.
                 Entries in this MIB are indexed by 
                 bsnAPDot3MacAddress and bsnAPIfSlotId"
        INDEX { bsnAPDot3MacAddress, bsnAPIfSlotId}
    ::= { bsnAPIfLoadParametersTable 1 }

BsnAPIfLoadParametersEntry ::=
                SEQUENCE {
                bsnAPIfLoadRxUtilization        INTEGER,
                bsnAPIfLoadTxUtilization        INTEGER,
                bsnAPIfLoadChannelUtilization   INTEGER,
                bsnAPIfLoadNumOfClients         Integer32,
                bsnAPIfPoorSNRClients           Integer32
                }

bsnAPIfLoadRxUtilization OBJECT-TYPE
      SYNTAX INTEGER(0..100)
      MAX-ACCESS read-only
      STATUS current
      DESCRIPTION
              "This is the percentage of time the Airespace AP 
              receiver is busy operating on packets. It is a number 
              from 0-100 representing a load from 0 to 1."
    ::= { bsnAPIfLoadParametersEntry 1}

bsnAPIfLoadTxUtilization OBJECT-TYPE
        SYNTAX INTEGER(0..100)
        MAX-ACCESS read-only
        STATUS current
        DESCRIPTION
                "This is the percentage of time the Airespace AP 
                 transmitter is busy operating on packets. It is a 
                 number from 0-100 representing a load from 0 to 1."
    ::= { bsnAPIfLoadParametersEntry 2}

bsnAPIfLoadChannelUtilization OBJECT-TYPE
        SYNTAX INTEGER(0..100)
        MAX-ACCESS read-only
        STATUS current
        DESCRIPTION
                "Channel Utilization"
    ::= { bsnAPIfLoadParametersEntry 3}

bsnAPIfLoadNumOfClients OBJECT-TYPE
     SYNTAX Integer32
     MAX-ACCESS read-only
     STATUS current
     DESCRIPTION
             "This is the number of clients attached to this Airespace 
              AP at the last measurement interval(This comes from 
              APF)"
    ::= { bsnAPIfLoadParametersEntry 4}

bsnAPIfPoorSNRClients OBJECT-TYPE
     SYNTAX Integer32
     MAX-ACCESS read-only
     STATUS current
     DESCRIPTION
             "This is the number of clients with poor SNR attached to 
              this Airespace AP at the last measurement interval 
              ( This comes from APF )."
    ::= { bsnAPIfLoadParametersEntry 24}


--********************************************************************
-- * End of bsnAPIfLoadParametersTable
--********************************************************************

--********************************************************************
-- * Begin of bsnAPIfChannelInterferenceInfoTable
--********************************************************************

bsnAPIfChannelInterferenceInfoTable OBJECT-TYPE
      SYNTAX SEQUENCE OF BsnAPIfChannelInterferenceInfoEntry
      MAX-ACCESS not-accessible
      STATUS current
      DESCRIPTION
              "This is a table of channel information like interference
               and noise from other 802.11 networks on each channel."
      ::= { bsnAP 14 }

bsnAPIfChannelInterferenceInfoEntry OBJECT-TYPE
       SYNTAX BsnAPIfChannelInterferenceInfoEntry
       MAX-ACCESS not-accessible
       STATUS current
       DESCRIPTION
               "An entry (conceptual row) in the Table.
                Entries in this MIB are indexed by 
                bsnAPDot3MacAddress, bsnAPIfSlotId"
       INDEX { bsnAPDot3MacAddress, bsnAPIfSlotId,
                bsnAPIfInterferenceChannelNo}
       ::= { bsnAPIfChannelInterferenceInfoTable 1 }

BsnAPIfChannelInterferenceInfoEntry ::=
                SEQUENCE {
                bsnAPIfInterferenceChannelNo     Integer32,
                bsnAPIfInterferencePower         Integer32,
                bsnAPIfInterferenceUtilization   INTEGER
                }

bsnAPIfInterferenceChannelNo OBJECT-TYPE
       SYNTAX Integer32
       MAX-ACCESS read-only
       STATUS current
       DESCRIPTION
               "Channel Number on AP"
    ::= { bsnAPIfChannelInterferenceInfoEntry 1}

bsnAPIfInterferencePower OBJECT-TYPE
       SYNTAX Integer32
       MAX-ACCESS read-only
       STATUS current
       DESCRIPTION
               "Power of Interference from other 802.11 networks on 
                this channel"
      ::= { bsnAPIfChannelInterferenceInfoEntry 2}

bsnAPIfInterferenceUtilization OBJECT-TYPE
       SYNTAX INTEGER(0..100)
       MAX-ACCESS read-only
       STATUS current
       DESCRIPTION
               "Interference from other 802.11 networks on this 
                channel"
      ::= { bsnAPIfChannelInterferenceInfoEntry 22}


--********************************************************************
-- * Begin of bsnAPIfRadarChannelStatisticsTable
--********************************************************************

bsnAPIfRadarChannelStatisticsTable OBJECT-TYPE
      SYNTAX SEQUENCE OF BsnAPIfRadarChannelStatisticsEntry
      MAX-ACCESS         not-accessible
      STATUS             current
      DESCRIPTION
              "This is a table of channel information on which radar 
               signal were detected. This will give the list of 
               channels and last heard timestamp. Radar signals are 
               detected only on 5Ghz range. 
               So this will be detected for 802.11a interface."
      ::= { bsnAP 24 }

bsnAPIfRadarChannelStatisticsEntry OBJECT-TYPE
       SYNTAX               BsnAPIfRadarChannelStatisticsEntry
       MAX-ACCESS           not-accessible
       STATUS current
       DESCRIPTION
               "An entry (conceptual row) in the Table.
                Entries in this MIB are indexed by bsnAPDot3MacAddress,
                bsnAPIfSlotId, bsnAPIfRadarDetectedCannelNumber."
       INDEX { bsnAPDot3MacAddress, bsnAPIfSlotId,
               bsnAPIfRadarDetectedChannelNumber }
      ::= { bsnAPIfRadarChannelStatisticsTable 1 }

BsnAPIfRadarChannelStatisticsEntry ::=
                SEQUENCE {
                   bsnAPIfRadarDetectedChannelNumber  Integer32,
                   bsnAPIfRadarSignalLastHeard        Integer32
                }

bsnAPIfRadarDetectedChannelNumber   OBJECT-TYPE
       SYNTAX                      Integer32
       MAX-ACCESS                  read-only
       STATUS current
       DESCRIPTION
               "Channel Number on which radar signals were detected."
    ::= { bsnAPIfRadarChannelStatisticsEntry 1}

bsnAPIfRadarSignalLastHeard        OBJECT-TYPE
       SYNTAX                      Integer32
       UNITS                       "seconds"
       MAX-ACCESS                  read-only
       STATUS                      current
       DESCRIPTION
               "This tells how many seconds ago radar signal was heard 
                on the channel."
    ::= { bsnAPIfRadarChannelStatisticsEntry 2}

--********************************************************************
-- * End of bsnAPIfRadarChannelInterferenceInfoTable
--********************************************************************

--********************************************************************
-- * Begin of bsnAPIfChannelNoiseInfoTable
--********************************************************************
bsnAPIfChannelNoiseInfoTable OBJECT-TYPE
      SYNTAX SEQUENCE OF BsnAPIfChannelNoiseInfoEntry
      MAX-ACCESS not-accessible
      STATUS current
      DESCRIPTION
              "This is a table of channel information like 
              interference and noise from other 802.11 networks on 
              each channel."
      ::= { bsnAP 15 }

bsnAPIfChannelNoiseInfoEntry OBJECT-TYPE
       SYNTAX BsnAPIfChannelNoiseInfoEntry
       MAX-ACCESS not-accessible
       STATUS current
       DESCRIPTION
               "An entry (conceptual row) in the Table.
                Entries in this MIB are indexed by bsnAPDot3MacAddress,
                bsnAPIfSlotId"
       INDEX { bsnAPDot3MacAddress, bsnAPIfSlotId,
               bsnAPIfNoiseChannelNo }
    ::= { bsnAPIfChannelNoiseInfoTable 1 }

BsnAPIfChannelNoiseInfoEntry ::=
                SEQUENCE {
                bsnAPIfNoiseChannelNo            Integer32,
                bsnAPIfDBNoisePower              Integer32
                }

bsnAPIfNoiseChannelNo OBJECT-TYPE
       SYNTAX Integer32
       MAX-ACCESS read-only
       STATUS current
       DESCRIPTION
               "Channel Number on AP"
    ::= { bsnAPIfChannelNoiseInfoEntry 1}

bsnAPIfDBNoisePower OBJECT-TYPE
                SYNTAX Integer32
                MAX-ACCESS read-only
                STATUS current
                DESCRIPTION
                      "This is the average noise power in dBm on 
                       each channel that is available to Airespace AP"
    ::= { bsnAPIfChannelNoiseInfoEntry 21}

--********************************************************************
-- * Begin of bsnAPIfProfileStateTable
--********************************************************************

bsnAPIfProfileStateTable OBJECT-TYPE
        SYNTAX SEQUENCE OF BsnAPIfProfileStateEntry
        MAX-ACCESS not-accessible
        STATUS current
        DESCRIPTION
                "This is a table of state of interference monitor
                 on each Airespace AP"
        ::= { bsnAP 16 }

bsnAPIfProfileStateEntry OBJECT-TYPE
       SYNTAX BsnAPIfProfileStateEntry
       MAX-ACCESS not-accessible
       STATUS current
       DESCRIPTION
               "An entry (conceptual row) in the Table.
                Entries in this MIB are indexed by bsnAPDot3MacAddress,
                bsnAPIfSlotId"
       INDEX { bsnAPDot3MacAddress, bsnAPIfSlotId}
        ::= { bsnAPIfProfileStateTable 1 }

BsnAPIfProfileStateEntry ::=
                SEQUENCE {
                bsnAPIfLoadProfileState          ProfileState,
                bsnAPIfInterferenceProfileState  ProfileState,
                bsnAPIfNoiseProfileState         ProfileState,
                bsnAPIfCoverageProfileState      ProfileState
              }

bsnAPIfLoadProfileState OBJECT-TYPE
      SYNTAX ProfileState
      MAX-ACCESS read-only
      STATUS current
      DESCRIPTION
              "This field represents the current state of the LOAD
               monitor. This is a total measurement of the business of
               this Airespace AP. PASS indicates that this Airespace 
               AP is performing adequately compared to the Airespace 
               AP profile. FAIL indicates the Airespace AP is not
               performing adequately against the LOAD profile."
    ::= { bsnAPIfProfileStateEntry 1}


bsnAPIfInterferenceProfileState OBJECT-TYPE
      SYNTAX ProfileState
      MAX-ACCESS read-only
      STATUS current
      DESCRIPTION
             "This field represents the current state of Interference
              monitor. This is a total measurement of the interference
              present at this Airespace AP. PASS indicates that this 
              Airespace AP is performing adequately compared to the 
              Interference profile.  FAIL indicates the Airespace AP 
              is not performing adequately against the Interference 
              profile."
    ::= { bsnAPIfProfileStateEntry 2}

bsnAPIfNoiseProfileState OBJECT-TYPE
        SYNTAX ProfileState
        MAX-ACCESS read-only
        STATUS current
        DESCRIPTION
            "This field represents the current state of Noise
             monitor. This is a total measurement of the noise
             present at this Airespace AP. PASS indicates that this 
             Airespace AP is performing adequately compared to the 
             noise profile.
             FAIL indicates the Airespace AP is not performing 
             adequately against the noise profile."
    ::= { bsnAPIfProfileStateEntry 3}

bsnAPIfCoverageProfileState OBJECT-TYPE
        SYNTAX ProfileState
        MAX-ACCESS read-only
        STATUS current
        DESCRIPTION
               "This field represents the current state of coverage
                monitor. This is a total measurement of the client 
                coverage at this Airespace AP. PASS indicates that 
                this  Airespace AP is performing adequately compared 
                to the  coverage profile. FAIL indicates the Airespace
                AP is not performing adequately against the coverage 
                profile."
    ::= { bsnAPIfProfileStateEntry 24}


--********************************************************************
-- * Begin of bsnAPIfRxNeighborsTable
--********************************************************************
bsnAPIfRxNeighborsTable OBJECT-TYPE
        SYNTAX SEQUENCE OF BsnAPIfRxNeighborsEntry
        MAX-ACCESS not-accessible
        STATUS current
        DESCRIPTION
                "This is a table of Rx Neighbors for each Airespace AP
                 with their RSSI value."
        ::= { bsnAP 17 }

bsnAPIfRxNeighborsEntry OBJECT-TYPE
        SYNTAX BsnAPIfRxNeighborsEntry
        MAX-ACCESS not-accessible
        STATUS current
        DESCRIPTION
                "An entry (conceptual row) in the Table.
                 Entries in this MIB are indexed by bsnAPDot3MacAddress
                 bsnAPIfSlotId, bsnAPIfRxNeighborMacAddress"
        INDEX { bsnAPDot3MacAddress, bsnAPIfSlotId,
                bsnAPIfRxNeighborMacAddress}
    ::= { bsnAPIfRxNeighborsTable 1 }

BsnAPIfRxNeighborsEntry ::=
                SEQUENCE {
                bsnAPIfRxNeighborMacAddress            MacAddress,
                bsnAPIfRxNeighborIpAddress             IpAddress,
                bsnAPIfRxNeighborRSSI                  Integer32,
                bsnAPIfRxNeighborSlot                  Integer32
                }

bsnAPIfRxNeighborMacAddress OBJECT-TYPE
                SYNTAX MacAddress
                MAX-ACCESS read-only
                STATUS current
                DESCRIPTION
                   "MAC Address of Rx Neighbor of the Airespace AP"
    ::= { bsnAPIfRxNeighborsEntry 1}

bsnAPIfRxNeighborIpAddress OBJECT-TYPE
                SYNTAX IpAddress
                MAX-ACCESS read-only
                STATUS current
                DESCRIPTION
                       "IP Address of Rx Neighbor of the Airespace AP"
    ::= { bsnAPIfRxNeighborsEntry 2}

bsnAPIfRxNeighborRSSI OBJECT-TYPE
                SYNTAX Integer32
                MAX-ACCESS read-only
                STATUS current
                DESCRIPTION
                       "RSSI value of the Rx Neighbor"
    ::= { bsnAPIfRxNeighborsEntry 3}

bsnAPIfRxNeighborSlot OBJECT-TYPE
                SYNTAX Integer32
                MAX-ACCESS read-only
                STATUS current
                DESCRIPTION
                       "Slot value of the Rx Neighbor"
    ::= { bsnAPIfRxNeighborsEntry 24}


--********************************************************************
-- * Begin of bsnMeshNodeTable
--********************************************************************
bsnMeshNodeTable OBJECT-TYPE
        SYNTAX SEQUENCE OF BsnMeshNodeEntry
        MAX-ACCESS not-accessible
        STATUS current
        DESCRIPTION
                "This is a table of mesh nodes."
        ::= { bsnAP 22 }

bsnMeshNodeEntry OBJECT-TYPE
        SYNTAX BsnMeshNodeEntry
        MAX-ACCESS not-accessible
        STATUS current
        DESCRIPTION
               "An entry (conceptual row) in the Table.
                Entries in this MIB are indexed by bsnAPDot3MacAddress"
        INDEX { bsnAPDot3MacAddress }
    ::= { bsnMeshNodeTable 1 }

BsnMeshNodeEntry ::=
                SEQUENCE {
                bsnMeshNodeRole                     INTEGER,
                bsnMeshNodeGroup                    OCTET STRING,
                bsnMeshNodeBackhaul                 INTEGER,
                bsnMeshNodeBackhaulPAP              INTEGER,
                bsnMeshNodeBackhaulRAP              INTEGER,
                bsnMeshNodeDataRate                 Integer32,
                bsnMeshNodeChannel                  Integer32,
                bsnMeshNodeRoutingState             INTEGER,
                bsnMeshNodeMalformedNeighPackets    Counter32,
                bsnMeshNodePoorNeighSnr             Counter32,
                bsnMeshNodeBlacklistPackets         Counter32,
                bsnMeshNodeInsufficientMemory       Counter32,
                bsnMeshNodeRxNeighReq               Counter32,
                bsnMeshNodeRxNeighRsp               Counter32,
                bsnMeshNodeTxNeighReq               Counter32,
                bsnMeshNodeTxNeighRsp               Counter32,
                bsnMeshNodeParentChanges            Counter32,
                bsnMeshNodeNeighTimeout             Counter32,
                bsnMeshNodeParentMacAddress         MacAddress,
                bsnMeshNodeAPType                   INTEGER,
                bsnMeshNodeEthernetBridge           INTEGER,
                bsnMeshNodeHops                     Integer32
                }

bsnMeshNodeRole OBJECT-TYPE
        SYNTAX INTEGER { pap(0), rap(1) }
        MAX-ACCESS read-only
        STATUS current
        DESCRIPTION
                "the role of this AP"
    ::= { bsnMeshNodeEntry 1}

bsnMeshNodeGroup OBJECT-TYPE
        SYNTAX OCTET STRING (SIZE(0..10))
        MAX-ACCESS read-only
        STATUS current
        DESCRIPTION
                "the bridge group name of this AP"
    ::= { bsnMeshNodeEntry 2 }

bsnMeshNodeBackhaul OBJECT-TYPE
        SYNTAX INTEGER { dot11a(0), dot11b(1), dot11g(2) }
        MAX-ACCESS read-only
        STATUS current
        DESCRIPTION
                "the backhaul radio device for this AP"
    ::= { bsnMeshNodeEntry 3 }


bsnMeshNodeBackhaulPAP OBJECT-TYPE
        SYNTAX INTEGER { auto(0), dot11a(1), dot11b(2), dot11g(3) }
        MAX-ACCESS read-only
        STATUS current
        DESCRIPTION
                "the backhaul "
    ::= { bsnMeshNodeEntry 4 }


bsnMeshNodeBackhaulRAP OBJECT-TYPE
        SYNTAX INTEGER { dot11a(0), dot11b(1), dot11g(2) }
        MAX-ACCESS read-write
        STATUS current
        DESCRIPTION
                "the backhaul radio device for this AP"
    ::= { bsnMeshNodeEntry 5 }

bsnMeshNodeDataRate OBJECT-TYPE
                SYNTAX Integer32
                MAX-ACCESS read-write
                STATUS current
                DESCRIPTION
                        "this nodes backhaul data rate"
    ::= { bsnMeshNodeEntry 6 }

bsnMeshNodeChannel OBJECT-TYPE
                SYNTAX Integer32
                MAX-ACCESS read-only
                STATUS current
                DESCRIPTION
                        "this nodes backhaul channel"
    ::= { bsnMeshNodeEntry 7 }

bsnMeshNodeRoutingState OBJECT-TYPE
        SYNTAX INTEGER { start(1), seek(2),
                         sync(3), auth(4),
                         maint(5) }
        MAX-ACCESS read-only
        STATUS current
        DESCRIPTION
            "routing state"
    ::= { bsnMeshNodeEntry 8 }

bsnMeshNodeMalformedNeighPackets OBJECT-TYPE
      SYNTAX Counter32
      MAX-ACCESS read-only
      STATUS current
      DESCRIPTION
            "the number of malformed neighbor packets."
      ::= { bsnMeshNodeEntry 9 }

bsnMeshNodePoorNeighSnr OBJECT-TYPE
      SYNTAX Counter32
      MAX-ACCESS read-only
      STATUS current
      DESCRIPTION
            "poor neighbor snr"
      ::= { bsnMeshNodeEntry 10 }

bsnMeshNodeBlacklistPackets OBJECT-TYPE
      SYNTAX Counter32
      MAX-ACCESS read-only
      STATUS current
      DESCRIPTION
            "the number of blacklist packets received"
      ::= { bsnMeshNodeEntry 11 }

bsnMeshNodeInsufficientMemory OBJECT-TYPE
      SYNTAX Counter32
      MAX-ACCESS read-only
      STATUS current
      DESCRIPTION
            "occurences of insufficient memory conditions"
      ::= { bsnMeshNodeEntry 12 }

bsnMeshNodeRxNeighReq OBJECT-TYPE
      SYNTAX Counter32
      MAX-ACCESS read-only
      STATUS current
      DESCRIPTION
            "Rx neighbor requests"
      ::= { bsnMeshNodeEntry 13 }

bsnMeshNodeRxNeighRsp OBJECT-TYPE
      SYNTAX Counter32
      MAX-ACCESS read-only
      STATUS current
      DESCRIPTION
            "Rx neighbor responses"
      ::= { bsnMeshNodeEntry 14 }

bsnMeshNodeTxNeighReq OBJECT-TYPE
      SYNTAX Counter32
      MAX-ACCESS read-only
      STATUS current
      DESCRIPTION
            "Tx neighbor requests"
      ::= { bsnMeshNodeEntry 15 }

bsnMeshNodeTxNeighRsp OBJECT-TYPE
      SYNTAX Counter32
      MAX-ACCESS read-only
      STATUS current
      DESCRIPTION
            "Tx neighbor responses"
      ::= { bsnMeshNodeEntry 16 }

bsnMeshNodeParentChanges OBJECT-TYPE
      SYNTAX Counter32
      MAX-ACCESS read-only
      STATUS current
      DESCRIPTION
            "number of parent changes"
      ::= { bsnMeshNodeEntry 17 }

bsnMeshNodeNeighTimeout OBJECT-TYPE
      SYNTAX Counter32
      MAX-ACCESS read-only
      STATUS current
      DESCRIPTION
            "number of neighbor timeouts"
      ::= { bsnMeshNodeEntry 18 }

bsnMeshNodeParentMacAddress OBJECT-TYPE
      SYNTAX MacAddress
      MAX-ACCESS read-only
      STATUS current
      DESCRIPTION
            "parents mac addressed"
      ::= { bsnMeshNodeEntry 19 }

bsnMeshNodeAPType OBJECT-TYPE
        SYNTAX INTEGER { indoorBridge(5), outdoorBridge(6) }
        MAX-ACCESS read-only
        STATUS current
        DESCRIPTION
                "the type of AP"
    ::= { bsnMeshNodeEntry 20 }

bsnMeshNodeEthernetBridge OBJECT-TYPE
        SYNTAX INTEGER { disable(0), enable(1) }
        MAX-ACCESS read-write
        STATUS current
        DESCRIPTION
                "enable  : Enables ethernet bridging on the AP.
                 disable : Disables ethernet bridging on the AP.
                 Changes are only applicable when AP is in 'Bridge' 
                 mode. "
    ::= { bsnMeshNodeEntry 21 }

bsnMeshNodeHops OBJECT-TYPE
      SYNTAX Integer32
      MAX-ACCESS read-only
      STATUS current
      DESCRIPTION
            "number of hops to rap"
      ::= { bsnMeshNodeEntry 30 }


--********************************************************************
-- * Begin of bsnMeshNeighsTable
--********************************************************************
bsnMeshNeighsTable OBJECT-TYPE
        SYNTAX SEQUENCE OF BsnMeshNeighsEntry
        MAX-ACCESS not-accessible
        STATUS current
        DESCRIPTION
                "This is a table of mesh neighbors."
        ::= { bsnAP 23 }

bsnMeshNeighsEntry OBJECT-TYPE
        SYNTAX BsnMeshNeighsEntry
        MAX-ACCESS not-accessible
        STATUS current
        DESCRIPTION
                "An entry (conceptual row) in the Table.
                 Entries in this MIB are indexed by bsnAPDot3MacAddress
                 and bsnMeshNeighNeighMacAddress"
        INDEX { bsnAPDot3MacAddress, bsnMeshNeighMacAddress }
    ::= { bsnMeshNeighsTable 1 }

BsnMeshNeighsEntry ::=
                SEQUENCE {
                bsnMeshNeighMacAddress                  MacAddress,
                bsnMeshNeighType                        INTEGER,
                bsnMeshNeighState                       INTEGER,
                bsnMeshNeighSnr                         Integer32,
                bsnMeshNeighSnrUp                       Integer32,
                bsnMeshNeighSnrDown                     Integer32,
                bsnMeshNeighLinkSnr                     Integer32,
                bsnMeshNeighAdjustedEase                Integer32,
                bsnMeshNeighUnadjustedEase              Integer32,
                bsnMeshNeighRapEase                     Integer32,
                bsnMeshNeighTxParent                    Counter32,
                bsnMeshNeighRxParent                    Counter32,
                bsnMeshNeighPoorSnr                     Counter32,
                bsnMeshNeighLastUpdate                  Integer32,
                bsnMeshNeighParentChange                Integer32
                }

bsnMeshNeighMacAddress OBJECT-TYPE
                SYNTAX MacAddress
                MAX-ACCESS read-only
                STATUS current
                DESCRIPTION
                        "MAC Address of neighbor"
    ::= { bsnMeshNeighsEntry 1 }

bsnMeshNeighType OBJECT-TYPE
                SYNTAX INTEGER { parent(0), tentparent(1), neigh(2), 
                                 blacklisted(3), child(4) }
                MAX-ACCESS read-only
                STATUS current
                DESCRIPTION
                        "neighbor type"
    ::= { bsnMeshNeighsEntry 2 }

bsnMeshNeighState OBJECT-TYPE
                SYNTAX INTEGER { updated(0), needupdate(1) }
                MAX-ACCESS read-only
                STATUS current
                DESCRIPTION
                        "neighbor state"
    ::= { bsnMeshNeighsEntry 3 }

bsnMeshNeighSnr OBJECT-TYPE
                SYNTAX Integer32
                MAX-ACCESS read-only
                STATUS current
                DESCRIPTION
                        "explicitly set SNR"
    ::= { bsnMeshNeighsEntry 4 }

bsnMeshNeighSnrUp OBJECT-TYPE
                SYNTAX Integer32
                MAX-ACCESS read-only
                STATUS current
                DESCRIPTION
                        "snr up"
    ::= { bsnMeshNeighsEntry 5 }


bsnMeshNeighSnrDown OBJECT-TYPE
                SYNTAX Integer32
                MAX-ACCESS read-only
                STATUS current
                DESCRIPTION
                        "snr down"
    ::= { bsnMeshNeighsEntry 6}


bsnMeshNeighLinkSnr OBJECT-TYPE
                SYNTAX Integer32
                MAX-ACCESS read-only
                STATUS current
                DESCRIPTION
                        "link snr"
    ::= { bsnMeshNeighsEntry 7}


bsnMeshNeighAdjustedEase OBJECT-TYPE
                SYNTAX Integer32
                MAX-ACCESS read-only
                STATUS current
                DESCRIPTION
                        "hops adjusted ease"
    ::= { bsnMeshNeighsEntry 8 }


bsnMeshNeighUnadjustedEase OBJECT-TYPE
                SYNTAX Integer32
                MAX-ACCESS read-only
                STATUS current
                DESCRIPTION
                        "ease to root AP from this AP"
    ::= { bsnMeshNeighsEntry 9 }


bsnMeshNeighRapEase OBJECT-TYPE
                SYNTAX Integer32
                MAX-ACCESS read-only
                STATUS current
                DESCRIPTION
                        "unadjusted ease received in last hello"
    ::= { bsnMeshNeighsEntry 10 }


bsnMeshNeighTxParent OBJECT-TYPE
                SYNTAX Counter32
                MAX-ACCESS read-only
                STATUS current
                DESCRIPTION
                        "tx packets to this node while a parent"
    ::= { bsnMeshNeighsEntry 11 }


bsnMeshNeighRxParent OBJECT-TYPE
                SYNTAX Counter32
                MAX-ACCESS read-only
                STATUS current
                DESCRIPTION
                        "rx packets from this node while a parent"
    ::= { bsnMeshNeighsEntry 12 }

bsnMeshNeighPoorSnr OBJECT-TYPE
                SYNTAX Counter32
                MAX-ACCESS read-only
                STATUS current
                DESCRIPTION
                        "packets with poor snr received from this node"
    ::= { bsnMeshNeighsEntry 13 }

bsnMeshNeighLastUpdate OBJECT-TYPE
                SYNTAX Integer32
                MAX-ACCESS read-only
                STATUS current
                DESCRIPTION
                        "last received hello from this neighbor"
    ::= { bsnMeshNeighsEntry 14 }

bsnMeshNeighParentChange OBJECT-TYPE
                SYNTAX Integer32
                MAX-ACCESS read-only
                STATUS current
                DESCRIPTION
                        "when this node last became parent"
    ::= { bsnMeshNeighsEntry 20 }

--********************************************************************
-- * Begin of bsnAPIfStationRSSICoverageInfoTable
--********************************************************************
bsnAPIfStationRSSICoverageInfoTable OBJECT-TYPE
      SYNTAX SEQUENCE OF BsnAPIfStationRSSICoverageInfoEntry
      MAX-ACCESS not-accessible
      STATUS current
      DESCRIPTION
              "This is a table of channel information like interference
               and noise from other 802.11 networks on each channel."
      ::= { bsnAP 18 }

bsnAPIfStationRSSICoverageInfoEntry OBJECT-TYPE
       SYNTAX BsnAPIfStationRSSICoverageInfoEntry
       MAX-ACCESS not-accessible
       STATUS current
       DESCRIPTION
               "An entry (conceptual row) in the Table.
                Entries in this MIB are indexed by bsnAPDot3MacAddress,
                bsnAPIfSlotId"
       INDEX { bsnAPDot3MacAddress, bsnAPIfSlotId,
                bsnAPIfStationRSSICoverageIndex}
    ::= { bsnAPIfStationRSSICoverageInfoTable 1 }

BsnAPIfStationRSSICoverageInfoEntry ::=
                SEQUENCE {
                bsnAPIfStationRSSICoverageIndex     Integer32,
                bsnAPIfRSSILevel                    Integer32,
                bsnAPIfStationCountOnRSSI           Integer32
                }

bsnAPIfStationRSSICoverageIndex OBJECT-TYPE
       SYNTAX Integer32
       MAX-ACCESS read-only
       STATUS current
       DESCRIPTION
               "RSSI Coverage Index on AP"
    ::= { bsnAPIfStationRSSICoverageInfoEntry 1}

bsnAPIfRSSILevel OBJECT-TYPE
       SYNTAX Integer32
       MAX-ACCESS read-only
       STATUS current
       DESCRIPTION
               "RSSI Level"
      ::= { bsnAPIfStationRSSICoverageInfoEntry 2}

bsnAPIfStationCountOnRSSI OBJECT-TYPE
                SYNTAX Integer32
                MAX-ACCESS read-only
                STATUS current
                DESCRIPTION
                        "Number of stations on this RSSI Level"
    ::= { bsnAPIfStationRSSICoverageInfoEntry 23}


-- ********************************************************************
-- * Begin of bsnAPIfStationSNRCoverageInfoTable
-- ********************************************************************
bsnAPIfStationSNRCoverageInfoTable OBJECT-TYPE
      SYNTAX SEQUENCE OF BsnAPIfStationSNRCoverageInfoEntry
      MAX-ACCESS not-accessible
      STATUS current
      DESCRIPTION
              "This is a table of Signal to Noise ratio Coverage 
               information on an AP Interface."
      ::= { bsnAP 19 }

bsnAPIfStationSNRCoverageInfoEntry OBJECT-TYPE
       SYNTAX BsnAPIfStationSNRCoverageInfoEntry
       MAX-ACCESS not-accessible
       STATUS current
       DESCRIPTION
               "An entry (conceptual row) in the Table.
                Entries in this MIB are indexed by bsnAPDot3MacAddress,
                bsnAPIfSlotId"
       INDEX { bsnAPDot3MacAddress, bsnAPIfSlotId,
                bsnAPIfStationSNRCoverageIndex}
    ::= { bsnAPIfStationSNRCoverageInfoTable 1 }

BsnAPIfStationSNRCoverageInfoEntry ::=
                SEQUENCE {
        bsnAPIfStationSNRCoverageIndex          Integer32,
                bsnAPIfSNRLevel                 Integer32,
                bsnAPIfStationCountOnSNR        Integer32
                }

bsnAPIfStationSNRCoverageIndex OBJECT-TYPE
       SYNTAX Integer32
       MAX-ACCESS read-only
       STATUS current
       DESCRIPTION
               "SNR Coverage Index on AP"
    ::= { bsnAPIfStationSNRCoverageInfoEntry 1}

bsnAPIfSNRLevel OBJECT-TYPE
       SYNTAX Integer32
       MAX-ACCESS read-only
       STATUS current
       DESCRIPTION
               "SNR Level"
      ::= { bsnAPIfStationSNRCoverageInfoEntry 2}

bsnAPIfStationCountOnSNR OBJECT-TYPE
                SYNTAX Integer32
                MAX-ACCESS read-only
                STATUS current
                DESCRIPTION
                      "Number of stations on this SNR Level"
    ::= { bsnAPIfStationSNRCoverageInfoEntry 23}


-- ********************************************************************
-- * Begin of bsnAPIfRecommendedRFParametersTable
-- ********************************************************************
bsnAPIfRecommendedRFParametersTable OBJECT-TYPE
      SYNTAX SEQUENCE OF BsnAPIfRecommendedRFParametersEntry
      MAX-ACCESS not-accessible
      STATUS current
      DESCRIPTION
        " This table list Best Channel,Best TxPowerLevel,
          Best RTSThreshold,Best FragmentationThreshold etc
          for this AP Interface as determined by RRM."
      ::= { bsnAP 20 }

bsnAPIfRecommendedRFParametersEntry OBJECT-TYPE
       SYNTAX BsnAPIfRecommendedRFParametersEntry
       MAX-ACCESS not-accessible
       STATUS current
       DESCRIPTION
               "An entry (conceptual row) in the Table.
                Entries in this MIB are indexed by bsnAPDot3MacAddress,
                bsnAPIfSlotId"
       INDEX { bsnAPDot3MacAddress, bsnAPIfSlotId}
    ::= { bsnAPIfRecommendedRFParametersTable 1 }

BsnAPIfRecommendedRFParametersEntry ::=
                SEQUENCE {
        bsnAPIfRecommendedChannelNumber             Integer32,
        bsnAPIfRecommendedTxPowerLevel              Integer32,
        bsnAPIfRecommendedRTSThreshold              Integer32,
        bsnAPIfRecommendedFragmentationThreshold    Integer32
                }

bsnAPIfRecommendedChannelNumber OBJECT-TYPE
       SYNTAX Integer32
       MAX-ACCESS read-only
       STATUS current
       DESCRIPTION
               "Recommended ChannelNumber by RRM for this APIf"
    ::= { bsnAPIfRecommendedRFParametersEntry 1}

bsnAPIfRecommendedTxPowerLevel OBJECT-TYPE
       SYNTAX Integer32
       MAX-ACCESS read-only
       STATUS current
       DESCRIPTION
               "Recommended TxPowerLevel by RRM for this APIf"
    ::= { bsnAPIfRecommendedRFParametersEntry 2}

bsnAPIfRecommendedRTSThreshold OBJECT-TYPE
       SYNTAX Integer32
       MAX-ACCESS read-only
       STATUS current
       DESCRIPTION
               "Recommended RTSThreshold by RRM for this APIf"
    ::= { bsnAPIfRecommendedRFParametersEntry 3}

bsnAPIfRecommendedFragmentationThreshold OBJECT-TYPE
       SYNTAX Integer32
       MAX-ACCESS read-only
       STATUS current
       DESCRIPTION
               "Recommended Fragmentation Threshold by RRM for this 
                APIf"
    ::= { bsnAPIfRecommendedRFParametersEntry 24}


-- *******************************************************************
-- * Global Dot11 Parameters
-- * Global Dot11 Parameters apply to all Wlan(ESS)
-- * These parameters are as defined in IEEE 802.11 Standard MIB
-- *******************************************************************

    bsnGlobalDot11Config OBJECT IDENTIFIER ::= {bsnGlobalDot11 1}

-- ********************************************************************
-- *  BSN Dot11 Global Universal Parameters that apply to both a and b
-- ********************************************************************
bsnGlobalDot11PrivacyOptionImplemented OBJECT-TYPE
        SYNTAX INTEGER {notimplemented(0),implemented(1)}
        MAX-ACCESS read-only
        STATUS current
        DESCRIPTION
            "This attribute, when true, shall indicate that the IEEE
            802.11 WEP option is implemented.  The default value of
            this attribute shall be false."
    ::= { bsnGlobalDot11Config 1 }

bsnGlobalDot11AuthenticationResponseTimeOut OBJECT-TYPE
        SYNTAX Unsigned32 (5..60)
        MAX-ACCESS read-write
        STATUS current
        DESCRIPTION
            "This attribute shall specify the number of TU that a
            responding STA should wait for the next frame in the
            authentication sequence."
    ::= { bsnGlobalDot11Config 2 }

bsnGlobalDot11MultiDomainCapabilityImplemented OBJECT-TYPE
         SYNTAX INTEGER {no(0),yes(1)}
         MAX-ACCESS read-only
         STATUS current
         DESCRIPTION
                 "This attribute, when TRUE, indicates that the
                 station implementation is capable of supporting
                 multiple regulatory domains.  The capability is
                 disabled, otherwise.  The default value of this
                 attribute is FALSE."
        ::= { bsnGlobalDot11Config 3 }

bsnGlobalDot11MultiDomainCapabilityEnabled OBJECT-TYPE
                SYNTAX INTEGER {no(0),yes(1)}
                MAX-ACCESS read-only
                STATUS current
                DESCRIPTION
                     "This attribute, when TRUE, indicates that the
                      capability of the station to operate in multiple
                      regulatory domains is enabled.  The capability is
                      disabled, otherwise.  The default value of this
                      attribute is FALSE."
        ::= { bsnGlobalDot11Config 4 }

bsnGlobalDot11CountryIndex OBJECT-TYPE
        SYNTAX INTEGER { usa(1),canada(2),france(3),japan(4),
                     mexico(5),spain(6),usalegacy(7),
                     korearepublic(8),australia(9),austria(10),
                     belgium(11),denmark(12),finland(13),
                     germany(14),greece(15),ireland(16),
                     italy(17),luxembourg(18),netherlands(19),
                     portugal(20),sweden(21),unitedkingdom(22),
                     none(23),india(24),hongkong(25),
                     switzerland(26),iceland(27),
                     norway(28),singapore(29),
                     thailand(30),taiwan(31),
                     cyprus(33),czechrepublic(34),estonia(35),
                     hungary(36),lithuania(37),latvia(38),
                     malaysia(39),newzealand(40),poland(41),
                     slovenia(42),slovakrepublic(43),southafrica(44),
                     usachan165(45),israel(46),israelOutdoor(47),
                     argentina(48), brazil(49),saudiArabia(51),
                     turkey(52), indonesia(53),china(54),
                     koreaExtended(55),japan2(56),gibraltar(57),
                     liechtenstein(58),malta(59),monaco(60),
                     romania(61),russianfederation(62),
                     chile(63),colombia(64),panama(65),
                     peru(66),venezuela(67),philippines(68)
                  }
        MAX-ACCESS read-write
        STATUS current
        DESCRIPTION
                "This attribute identifies the country in which the
                station is operating."
        ::= { bsnGlobalDot11Config 5 }

bsnGlobalDot11LoadBalancing OBJECT-TYPE
    SYNTAX INTEGER { disable(0) , enable (1)}
    MAX-ACCESS read-write
    STATUS current
    DESCRIPTION
        "This attribute specifies if load balancing of clients is 
         enabled on disabled."
        ::= { bsnGlobalDot11Config 6 }

bsnGlobalDot11RogueTimer OBJECT-TYPE
    SYNTAX Integer32 (120..3600)
    MAX-ACCESS read-write
    STATUS current
    DESCRIPTION
        "This attribute specifies in seconds, the time interval after 
         which a Rogue Entry in Rogue Table will expire if no beacon 
         is heard from a Rogue."
        ::= { bsnGlobalDot11Config 7 }

bsnPrimaryMwarForAPs  OBJECT-TYPE
    SYNTAX INTEGER {disable(0), enable (1) }
    MAX-ACCESS read-write
    STATUS current
    DESCRIPTION
        "This attribute specifies if this Switch acts a Master Switch 
         for the Airespace APs.
         So if an Airespace AP doesn't find its Primary Switch, it will
         associate with this Switch."
    ::= { bsnGlobalDot11Config 8 }

bsnRtpProtocolPriority  OBJECT-TYPE
    SYNTAX INTEGER {nopriority(0), highpriority (1) }
    MAX-ACCESS read-write
    STATUS current
    DESCRIPTION
    " Real Time Protocol Priority."
    ::= { bsnGlobalDot11Config 9 }

bsnSystemCurrentTime OBJECT-TYPE
    SYNTAX DisplayString
    MAX-ACCESS read-only
    STATUS current
    DESCRIPTION
    "This attribute will display the Current System time on the 
     Switch."
    ::= { bsnGlobalDot11Config 10 }

bsnUpdateSystemTime OBJECT-TYPE
    SYNTAX DisplayString (SIZE(0..32))
    MAX-ACCESS read-write
    STATUS current
    DESCRIPTION
    "Use this attribute to change the System time on the Switch.
     Specify the new time in this Format MM/DD/YYYY HH:MM:SS"
    ::= { bsnGlobalDot11Config 11 }

bsnOperatingTemperatureEnvironment OBJECT-TYPE
    SYNTAX INTEGER { commercial(1), industrial(2),unknown(0)}
    MAX-ACCESS read-only
    STATUS current
    DESCRIPTION
    "Operating Environment of the Airespace Switch.
     commercial is Commercial (0 to 40 C) and
     industrial is Industrial (-10 to 70 C)"
    ::= { bsnGlobalDot11Config 12 }

bsnSensorTemperature OBJECT-TYPE
    SYNTAX Integer32
    MAX-ACCESS read-only
    STATUS current
    DESCRIPTION
    "Current Internal Temperature of the unit in Centigrade"
    ::= { bsnGlobalDot11Config 13 }

bsnTemperatureAlarmLowLimit OBJECT-TYPE
    SYNTAX Integer32
    MAX-ACCESS read-only
    STATUS current
    DESCRIPTION
    "Internal Temperature Alarm Low Limit in Centigrade. If the 
     bsnSensorTemperature goes below this limit 
     bsnSensedTemperatureTooLow Alarm will be sent out"
    ::= { bsnGlobalDot11Config 14 }

bsnTemperatureAlarmHighLimit OBJECT-TYPE
    SYNTAX Integer32
    MAX-ACCESS read-only
    STATUS current
    DESCRIPTION
    "Internal Temperature Alarm High Limit in Centigrade. If the 
     bsnSensorTemperature goes above this limit 
     bsnSensedTemperatureTooHigh Alarm will be sent out"
    ::= { bsnGlobalDot11Config 15 }

bsnVirtualGatewayAddress  OBJECT-TYPE
    SYNTAX  IpAddress
    MAX-ACCESS  read-write
    STATUS  current
    DESCRIPTION
        "Virtual Gateway Address of the Switch. This is used by web 
         auth and Ipsec. If the virtual IP Address is changed, the 
         Switch has to be rebooted for the new Address to take effect. 
         This is now replaced by the Virtual Interface in bsnswitching
         MIB."
    ::= {  bsnGlobalDot11Config 16 }

bsnRFMobilityDomainName OBJECT-TYPE
        SYNTAX OCTET STRING (SIZE(0..32))
        MAX-ACCESS read-write
        STATUS current
        DESCRIPTION
        "RF Mobility Group Name to which this Airespace Switch belongs.
         Airespace Switches on a network form a RF Group as well as a
         Mobility Group. RF Groups does the channel and power 
         management of AP while Mobility Group does load balancing and 
         hand off for clients."
    ::= { bsnGlobalDot11Config 17 }


bsnClientWatchListFeature OBJECT-TYPE
        SYNTAX INTEGER { disable (0), enable (1) }
        MAX-ACCESS read-write
        STATUS current
        DESCRIPTION
            "This flag should be turned on for the client watch lists 
             to be enabled on the switch. When enabled, the switch 
             generates Client Association and Authentication traps for
             the watchlisted clients."
        DEFVAL { disable }
        ::= { bsnGlobalDot11Config 18 }

bsnRogueLocationDiscoveryProtocol OBJECT-TYPE
        SYNTAX INTEGER { disable (0), enable (1)}
        MAX-ACCESS read-write
        STATUS current
        DESCRIPTION
                 "This flag should be turned on to enable the Rogue 
                  Location Discovery Protocol feature on the switch."
        DEFVAL { disable }
        ::= { bsnGlobalDot11Config 19 }

bsnRogueAutoContainFeature OBJECT-TYPE
        SYNTAX INTEGER { disable (0), enable (1)}
        MAX-ACCESS read-write
        STATUS current
        DESCRIPTION
                "This flag should be turned on to allow the switch to 
                 contain the rogues automatically if detected
                 on the wired network."
        DEFVAL { disable }
        ::= { bsnGlobalDot11Config 20 }

bsnOverAirProvisionApMode OBJECT-TYPE
        SYNTAX INTEGER { disable (0), enable (1)}
        MAX-ACCESS read-write
        STATUS current
        DESCRIPTION
                 "Over the Air Provisioning Mode for APs"
        ::= { bsnGlobalDot11Config 21 }

bsnMaximumNumberOfConcurrentLogins OBJECT-TYPE
        SYNTAX Integer32 (0..8)
        MAX-ACCESS read-write
        STATUS current
        DESCRIPTION
                 "This attribute specifies the maximum number of 
                  concurrent logins that the switch will allow for a 
                  single user. A value 0 implies that there is 
                  no restriction on the number of concurrent logins 
                  with a single username."
        ::= { bsnGlobalDot11Config 22 }

bsnAutoContainRoguesAdvertisingSsid OBJECT-TYPE
        SYNTAX INTEGER { alarmOnly (0), contain (1)}
        MAX-ACCESS read-write
        STATUS current
        DESCRIPTION
                 "This flag should be set to 1 to allow the switch to 
                  contain automatically those rogues that are 
                  advertising our SSID. If value is 0, only an alarm 
                  will be generated when such a rogue is detected."
        DEFVAL { alarmOnly }
        ::= { bsnGlobalDot11Config 23 }

bsnAutoContainAdhocNetworks OBJECT-TYPE
        SYNTAX INTEGER { alarmOnly (0), contain (1)}
        MAX-ACCESS read-write
        STATUS current
        DESCRIPTION
                 "This flag should be set to 1 to allow the switch to 
                  contain automatically the adhoc networks
                  detected by the switch. If value is 0, only an alarm 
                  will be generated when such a network is detected."
        DEFVAL { alarmOnly }
        ::= { bsnGlobalDot11Config 24 }

bsnAutoContainTrustedClientsOnRogueAps OBJECT-TYPE
        SYNTAX INTEGER { alarmOnly (0), contain (1)}
        MAX-ACCESS read-write
        STATUS current
        DESCRIPTION
                 "This flag should be set to 1 to allow the switch to 
                  contain automatically those trusted clients that
                  are associated to rogue APs. If value is 0, only an 
                  alarm will be generated when such a client is 
                  detected."
        DEFVAL { alarmOnly }
        ::= { bsnGlobalDot11Config 25 }

bsnValidateRogueClientsAgainstAAA OBJECT-TYPE
        SYNTAX INTEGER { disable (0), enable (1)}
        MAX-ACCESS read-write
        STATUS current
        DESCRIPTION
                 "This flag should be turned on to allow the switch to
                  validate 'valid' mobiles associating with rogue APs.
                  For example, if a client's MAC Address is found in 
                  the local MAC filter table, that client can be 
                  validated."
        DEFVAL { disable }
        ::= { bsnGlobalDot11Config 26 }

bsnSystemTimezoneDelta OBJECT-TYPE
        SYNTAX Integer32
        MAX-ACCESS read-write
        STATUS current
        DESCRIPTION
            "The delta (difference) between the local time and the 
             Universal Coordinated Time in hours.
             For example, it is -8 for the PST and +1 for France. If 
             the delta is -5.30 then this attribute will store -5 and 
             bsnSystemTimezoneDeltaMinutes will store 30. This value i
             should be between -23 to +23 "
        ::= { bsnGlobalDot11Config 27 }

bsnSystemTimezoneDeltaMinutes OBJECT-TYPE
        SYNTAX Integer32
        MAX-ACCESS read-write
        STATUS current
        DESCRIPTION
            "The minutes component of delta (difference) between the 
             local time and the Universal Coordinated Time."
        ::= { bsnGlobalDot11Config 30 }

bsnSystemTimezoneDaylightSavings OBJECT-TYPE
        SYNTAX INTEGER { disable(0), enable(1) }
        MAX-ACCESS read-write
        STATUS current
        DESCRIPTION
            "This flag specifies if daylight savings are enabled for 
             the current timezone."
        ::= { bsnGlobalDot11Config 28 }

bsnAllowAuthorizeApAgainstAAA OBJECT-TYPE
        SYNTAX INTEGER { disable(0), enable(1) }
        MAX-ACCESS read-write
        STATUS current
        DESCRIPTION
            "This flag specifies if LWAPP is allowed to get 
             authorization via RADIUS or local database for an AP."
        ::= { bsnGlobalDot11Config 29 }

bsnApFallbackEnabled OBJECT-TYPE
        SYNTAX INTEGER { disable(0), enable(1) }
        MAX-ACCESS read-write
        STATUS current
        DESCRIPTION
            "This flag specifies if the APs should continue LWAPP 
             discoveries to fallback to the primary switch
             in case they are not already associated with it i.e they 
             are associated with their respective secondary or 
             tertiary switch instead."
        ::= { bsnGlobalDot11Config 31 }

bsnAppleTalkEnabled OBJECT-TYPE
        SYNTAX INTEGER { disable(0), enable(1) }
        MAX-ACCESS read-write
        STATUS current
        DESCRIPTION
            "This flag turns on the appletalk bridging in the switch 
             such that the packets from Apple clients that use
             appletalk format can be processed by the switch. When 
             this flag is off, these packets are dropped."
        ::= { bsnGlobalDot11Config 32 }

-- ********************************************************************
-- *  Global Trusted AP policies
-- ********************************************************************
  
  bsnTrustedApPolicyConfig OBJECT IDENTIFIER ::= 
                                        {bsnGlobalDot11Config 40}


bsnPolicyForMisconfiguredAps OBJECT-TYPE
        SYNTAX INTEGER { alarmOnly (0), contain (1)}
        MAX-ACCESS read-write
        STATUS current
        DESCRIPTION
                 "This flag should be turned on to allow the switch to 
                  contain misconfigured APs."
        DEFVAL { alarmOnly }
        ::= { bsnTrustedApPolicyConfig 1 }

bsnEncryptionPolicyEnforced OBJECT-TYPE
        SYNTAX INTEGER { none(0), open(1),
                        wep(2), wpa(3)}
        MAX-ACCESS read-write
        STATUS current
        DESCRIPTION
                 "The encryption policy that is enforced on the 
                 trusted APs."
        DEFVAL { none }
        ::= { bsnTrustedApPolicyConfig 2 }

bsnPreamblePolicyEnforced OBJECT-TYPE
        SYNTAX INTEGER { none(0), short(1), long(2)}
        MAX-ACCESS read-write
        STATUS current
        DESCRIPTION
                 "The preamble policy that is enforced on the trusted 
                  APs."
        DEFVAL { none }
        ::= { bsnTrustedApPolicyConfig 3 }

bsnDot11ModePolicyEnforced OBJECT-TYPE
        SYNTAX INTEGER { none(0), dcfOnly(1), pcfOnly(2)}
        MAX-ACCESS read-write
        STATUS current
        DESCRIPTION
                 "The 802.11 Mode policy that is enforced on the 
                  trusted APs."
        DEFVAL { none }
        ::= { bsnTrustedApPolicyConfig 4 }

bsnRadioTypePolicyEnforced OBJECT-TYPE
        SYNTAX INTEGER { none(0), aOnly(1),
                        bOnly(2), bgOnly(3)}
        MAX-ACCESS read-write
        STATUS current
        DESCRIPTION
                 "The radio type policy that is enforced on the 
                 trusted
                  APs."
        DEFVAL { none }
        ::= { bsnTrustedApPolicyConfig 5 }

bsnValidateSsidForTrustedAp OBJECT-TYPE
        SYNTAX INTEGER { disable (0), enable (1)}
        MAX-ACCESS read-write
        STATUS current
        DESCRIPTION
                 "If enabled, the SSID of trusted APs will be 
                 validated
                  by the switch."
        DEFVAL { disable }
        ::= { bsnTrustedApPolicyConfig 6 }

bsnAlertIfTrustedApMissing OBJECT-TYPE
        SYNTAX INTEGER { disable (0), enable (1)}
        MAX-ACCESS read-write
        STATUS current
        DESCRIPTION
                 "If enabled, an alert will be generated when a 
                 trusted AP is missing."
        DEFVAL { disable }
        ::= { bsnTrustedApPolicyConfig 7 }

bsnTrustedApEntryExpirationTimeout OBJECT-TYPE
    SYNTAX Integer32 (120..3600)
    MAX-ACCESS read-write
    STATUS current
    DESCRIPTION
        "This attribute specifies in seconds, the time interval after 
         which a Trusted AP Entry will expire if no beacon is heard 
         from that AP."
        DEFVAL { 120 }
        ::= { bsnTrustedApPolicyConfig 8 }

  
--*******************************************************************
-- *  Global Trusted AP policies
--*******************************************************************

  bsnClientExclusionPolicyConfig OBJECT IDENTIFIER ::= 
                                              {bsnGlobalDot11Config 41}

bsnExcessive80211AssocFailures OBJECT-TYPE
        SYNTAX INTEGER { disable (0), enable (1)}
        MAX-ACCESS read-write
        STATUS current
        DESCRIPTION
                 "This flag specifies if client should be excluded
                  (blacklisted) if repeated 802.11 Association 
                  Failures occurs with a client."        
        ::= { bsnClientExclusionPolicyConfig 1 }

bsnExcessive80211AuthFailures OBJECT-TYPE
        SYNTAX INTEGER { disable (0), enable (1)}
        MAX-ACCESS read-write
        STATUS current
        DESCRIPTION
                 "This flag specifies if client should be excluded
                  (blacklisted) if repeated 802.11 Authentication 
                  Failures occurs with a client."        
        ::= { bsnClientExclusionPolicyConfig 2 }

bsnExcessive8021xAuthFailures OBJECT-TYPE
        SYNTAX INTEGER { disable (0), enable (1)}
        MAX-ACCESS read-write
        STATUS current
        DESCRIPTION
                 "This flag specifies if client should be excluded
                  (blacklisted) if repeated 802.1x Authentication 
                  Failures occurs with a client."        
        ::= { bsnClientExclusionPolicyConfig 3 }
        
bsnExternalPolicyServerFailures OBJECT-TYPE
        SYNTAX INTEGER { disable (0), enable (1)}
        MAX-ACCESS read-write
        STATUS current
        DESCRIPTION
                 "This flag specifies if client should be excluded
                  (blacklisted) if repeated external policy server 
                  failures occurs with a client."
        ::= { bsnClientExclusionPolicyConfig 4 }

bsnExcessiveWebAuthFailures OBJECT-TYPE
        SYNTAX INTEGER { disable (0), enable (1)}
        MAX-ACCESS read-write
        STATUS current
        DESCRIPTION
                 "This flag specifies if client should be excluded
                  (blacklisted) if repeated Web Authentication Failures
                  occurs with a client."
        ::= { bsnClientExclusionPolicyConfig 5 }

bsnIPTheftORReuse OBJECT-TYPE
        SYNTAX INTEGER { disable (0), enable (1)}
        MAX-ACCESS read-write
        STATUS current
        DESCRIPTION
                 "This flag specifies if client should be excluded
                  (blacklisted) if it appears to be reusing an IP 
                  Address.(Possible IP Theft)"
        ::= { bsnClientExclusionPolicyConfig 6 }


-- *******************************************************************
-- *  Standard and Custom Signature Lists. Signatures are pattern 
-- *  matching rules used to identify packets
-- *  that may be a part of an attack.
-- ********************************************************************
bsnSignatureConfig OBJECT IDENTIFIER ::= {bsnGlobalDot11Config 42}

bsnStandardSignatureTable OBJECT-TYPE
      SYNTAX     SEQUENCE OF BsnStandardSignatureEntry
      MAX-ACCESS not-accessible
      STATUS     current
      DESCRIPTION
            "The table listing Standard Signatures configured on the 
             switch. The standard signatures are provided with the 
             released product. The standard signatures can be updated
             via file download to the switch. The table is indexed by 
             the precedence of the signatures."
      ::= { bsnSignatureConfig 1 }

bsnStandardSignatureEntry OBJECT-TYPE
      SYNTAX     BsnStandardSignatureEntry
      MAX-ACCESS not-accessible
      STATUS     current
      DESCRIPTION
            "...."
      INDEX      { bsnStandardSignaturePrecedence }
      ::= { bsnStandardSignatureTable 1 }

BsnStandardSignatureEntry ::= SEQUENCE {
           bsnStandardSignaturePrecedence               Unsigned32,
           bsnStandardSignatureName                     DisplayString,
           bsnStandardSignatureDescription              DisplayString,
           bsnStandardSignatureFrameType                INTEGER,
           bsnStandardSignatureAction                   INTEGER,
           bsnStandardSignatureState                    INTEGER,
           bsnStandardSignatureFrequency                Unsigned32,
           bsnStandardSignatureQuietTime                Unsigned32,
           bsnStandardSignatureVersion                  Unsigned32,
           bsnStandardSignatureConfigType               INTEGER,
           bsnStandardSignatureRowStatus                RowStatus,
           bsnStandardSignatureEnable                   TruthValue,
           bsnStandardSignatureMacInfo      BsnTxtSignatureMacInfo,
           bsnStandardSignatureMacFreq                  Unsigned32
      }

bsnStandardSignaturePrecedence OBJECT-TYPE
      SYNTAX Unsigned32(1..100)
      MAX-ACCESS read-only
      STATUS     current
      DESCRIPTION
             "Precedence of the signature. This specifies the order in
              which the signature is applied to a packet."
      ::= { bsnStandardSignatureEntry 1 }

bsnStandardSignatureName OBJECT-TYPE
      SYNTAX DisplayString (SIZE(0..20))
      MAX-ACCESS read-only
      STATUS     current
      DESCRIPTION
             "This attribute is used to configure the name on a 
              signature."
      ::= { bsnStandardSignatureEntry 2 }

bsnStandardSignatureDescription OBJECT-TYPE
      SYNTAX DisplayString (SIZE(0..100))
      MAX-ACCESS read-only
      STATUS     current
      DESCRIPTION
             "This attribute is used to configure the description of a
              signature."
      ::= { bsnStandardSignatureEntry 3 }

bsnStandardSignatureFrameType OBJECT-TYPE
      SYNTAX     INTEGER { management(0) , data (1)}
      MAX-ACCESS read-only
      STATUS     current
      DESCRIPTION
             "This attribute specifies the type of frame that needs to
              match a signature."
      ::= { bsnStandardSignatureEntry 4 }

bsnStandardSignatureAction OBJECT-TYPE
      SYNTAX     INTEGER { none (0) , report (1), 
                           contain(2), exclude(3) }
      MAX-ACCESS read-only
      STATUS     current
      DESCRIPTION
             "This attribute specifies the action to be taken once a 
              packet is found to match a signature."
      ::= { bsnStandardSignatureEntry 5 }

bsnStandardSignatureState OBJECT-TYPE
      SYNTAX     INTEGER { disabled(0) , enabled(1) }
      MAX-ACCESS read-only
      STATUS     current
      DESCRIPTION
             "This attribute specifies the state of a signature. It 
              is used to match packets only if the state is enabled."
      ::= { bsnStandardSignatureEntry 6 }

bsnStandardSignatureFrequency OBJECT-TYPE
      SYNTAX Unsigned32(0..65535)
      MAX-ACCESS read-only
      STATUS     current
      DESCRIPTION
             "This specifies the frequency of the matching packets 
              after which the specified action is taken."
      ::= { bsnStandardSignatureEntry 7 }

bsnStandardSignatureQuietTime OBJECT-TYPE
      SYNTAX Unsigned32(0..65535)
      MAX-ACCESS read-only
      STATUS     current
      DESCRIPTION
             "This specifies the quiet time in seconds during which no
              matching packets are found after which the attack is 
              considered stopped."
      ::= { bsnStandardSignatureEntry 8 }

bsnStandardSignatureVersion OBJECT-TYPE
      SYNTAX Unsigned32(0..128)
      MAX-ACCESS read-only
      STATUS     current
      DESCRIPTION
             "This specifies the signature version."
      ::= { bsnStandardSignatureEntry 9 }

bsnStandardSignatureConfigType OBJECT-TYPE
      SYNTAX     INTEGER { pattern(0) , protocol(1) }
      MAX-ACCESS read-only
      STATUS     current
      DESCRIPTION
             "This attribute specifies the type of Signature 
              configuration. It's protocol when the protocol format is
              used in the UI to configure this. Pattern is the config 
              type for all signatures in the released signature file 
              and when signatures are configured using pattern
              format. Note: the signatures will be allowed to be i
              configured in later releases."
      ::= { bsnStandardSignatureEntry 10 }

bsnStandardSignatureEnable OBJECT-TYPE
      SYNTAX     TruthValue
      MAX-ACCESS read-write
      STATUS     current
      DESCRIPTION
              "This object configures the status of a particular
              standard signature on LWAPP APs, for use in performing
              signature analysis on the received 802.11 data and/or
              management frames.

              A value of 'true' makes the Controller send the
              'Signature Add LWAPP Message' to all the joined APs
              with the status field set to 'enable'.  This makes
              the joined APs perform signature analysis on the
              received 802.11 data and/or management frames and
              report the discrepancies observed, if any, to the
              Controller.

              A value of 'false' makes the Controller send the
              'Signature Add LWAPP Message' to all the joined APs
              with the status field set to 'disable'.  The joined
              APs doesn't perform the signature analysis on the
              received 802.11 data and/or management frames for
              this particular signature, till the signature is
              enabled. "
      DEFVAL  { false }
      ::= { bsnStandardSignatureEntry 11 }

bsnStandardSignatureMacInfo OBJECT-TYPE
        SYNTAX     BsnTxtSignatureMacInfo
        MAX-ACCESS read-only
        STATUS     current
        DESCRIPTION
                "This object defines the pattern followed by the
                LWAPP APs to perform signature analysis with this
                Standard signature and report the results to the
                Controller. "
      ::= { bsnStandardSignatureEntry 12 }

bsnStandardSignatureMacFreq OBJECT-TYPE
        SYNTAX     Unsigned32(0..65535)
        MAX-ACCESS read-only
        STATUS     current
        DESCRIPTION
                "This object specifies the frequency of matching
                packets from a particular source after which the
                specified action is taken. "
        ::= { bsnStandardSignatureEntry 13 }

bsnStandardSignatureRowStatus  OBJECT-TYPE
      SYNTAX RowStatus
      MAX-ACCESS read-only
      STATUS current
      DESCRIPTION
      " Row Status for creation/deletion. Signature will allowed to
        be created, deleted and edited in later releases."
      ::= { bsnStandardSignatureEntry 20 }

--*******************************************************************
-- *  Packet Matching Patterns of a Standard Signature
--*******************************************************************

bsnStandardSignaturePatternTable OBJECT-TYPE
      SYNTAX     SEQUENCE OF BsnStandardSignaturePatternEntry
      MAX-ACCESS not-accessible
      STATUS     current
      DESCRIPTION
            "The table listing the matching patterns specified for a i
             Standard Signature. These are instrumental in
             matching the signature with a packet. A maximum of 5 i
             patterns may be specifed for a signature.
             These are used for matching in the order of their index."
      ::= { bsnSignatureConfig 2 }

bsnStandardSignaturePatternEntry OBJECT-TYPE
      SYNTAX     BsnStandardSignaturePatternEntry
      MAX-ACCESS not-accessible
      STATUS     current
      DESCRIPTION
            "...."
      INDEX      { bsnStandardSignaturePrecedence, 
                   bsnStandardSignaturePatternIndex }
      ::= { bsnStandardSignaturePatternTable 1 }

BsnStandardSignaturePatternEntry ::= SEQUENCE {
     bsnStandardSignaturePatternIndex          Unsigned32,
     bsnStandardSignaturePatternOffset         Unsigned32,
     bsnStandardSignaturePatternString         DisplayString,
     bsnStandardSignaturePatternMask           DisplayString,
     bsnStandardSignaturePatternOffSetStart 
                                        BsnSignaturePatternOffSetStart,
     bsnStandardSignaturePatternRowStatus      RowStatus
   }

bsnStandardSignaturePatternIndex OBJECT-TYPE
      SYNTAX Unsigned32(1..5)
      MAX-ACCESS read-only
      STATUS     current
      DESCRIPTION
             "Index of the pattern. This specifies the order in which 
              the pattern is checked against the packet contents."
      ::= { bsnStandardSignaturePatternEntry 1 }

bsnStandardSignaturePatternOffset OBJECT-TYPE
      SYNTAX Unsigned32(0..128)
      MAX-ACCESS read-only
      STATUS     current
      DESCRIPTION
             "Offset from the start of the packet where the AP looks 
              for a match to the pattern."
      ::= { bsnStandardSignaturePatternEntry 2 }

bsnStandardSignaturePatternString OBJECT-TYPE
      SYNTAX DisplayString (SIZE(0..62))
      MAX-ACCESS read-only
      STATUS     current
      DESCRIPTION
             "This is the pattern string that the AP uses to match at 
              the offset. Example: 0x616c7068615f3178"
      ::= { bsnStandardSignaturePatternEntry 3 }

bsnStandardSignaturePatternMask OBJECT-TYPE
      SYNTAX DisplayString (SIZE(0..62))
      MAX-ACCESS read-only
      STATUS     current
      DESCRIPTION
             "This is the pattern mask. This is the bit mask that the 
              AP uses to mask out the bits in the packet at the given 
              offset. Example: 0xffffffffffffffff"
      ::= { bsnStandardSignaturePatternEntry 4 }

bsnStandardSignaturePatternOffSetStart OBJECT-TYPE
        SYNTAX     BsnSignaturePatternOffSetStart 
        MAX-ACCESS read-only
        STATUS     current
        DESCRIPTION
               "This object indicates how an offset should be applied
                while doing signature analysis for QOS and non-QOS
                data frames with this standard signature. "
      ::= { bsnStandardSignaturePatternEntry 5 }

bsnStandardSignaturePatternRowStatus  OBJECT-TYPE
      SYNTAX RowStatus
      MAX-ACCESS read-only
      STATUS current
      DESCRIPTION
      "Row Status for creation/deletion. Signature Pattern will allowed
       to be created, deleted and edited in later releases."
      ::= { bsnStandardSignaturePatternEntry 15 }

--********************************************************************
-- *  Custom Signature List.
--********************************************************************

bsnCustomSignatureTable OBJECT-TYPE
      SYNTAX     SEQUENCE OF BsnCustomSignatureEntry
      MAX-ACCESS not-accessible
      STATUS     current
      DESCRIPTION
            "The table listing Standard Signatures configured on the 
             switch. The standard signatures are provided
             with the released product. The standard signatures can be
             updated via file download to the switch. The table
             is indexed by the precedence of the signatures."
      ::= { bsnSignatureConfig 3 }

bsnCustomSignatureEntry OBJECT-TYPE
      SYNTAX     BsnCustomSignatureEntry
      MAX-ACCESS not-accessible
      STATUS     current
      DESCRIPTION
            "...."
      INDEX      { bsnCustomSignaturePrecedence }
      ::= { bsnCustomSignatureTable 1 }

BsnCustomSignatureEntry ::= SEQUENCE {
              bsnCustomSignaturePrecedence             Unsigned32,
              bsnCustomSignatureName                   DisplayString,
              bsnCustomSignatureDescription            DisplayString,
              bsnCustomSignatureFrameType              INTEGER,
              bsnCustomSignatureAction                 INTEGER,
              bsnCustomSignatureState                  INTEGER,
              bsnCustomSignatureFrequency              Unsigned32,
              bsnCustomSignatureQuietTime              Unsigned32,
              bsnCustomSignatureVersion                Unsigned32,
              bsnCustomSignatureConfigType             INTEGER,
              bsnCustomSignatureRowStatus              RowStatus,
              bsnCustomSignatureEnable                 TruthValue,
              bsnCustomSignatureMacInfo                
                                              BsnTxtSignatureMacInfo,
              bsnCustomSignatureMacFreq                Unsigned32

}

bsnCustomSignaturePrecedence OBJECT-TYPE
      SYNTAX Unsigned32(1..100)
      MAX-ACCESS read-only
      STATUS     current
      DESCRIPTION
             "Precedence of the signature. This specifies the order in 
              which the signature is applied to a packet."
      ::= { bsnCustomSignatureEntry 1 }

bsnCustomSignatureName OBJECT-TYPE
      SYNTAX DisplayString (SIZE(0..20))
      MAX-ACCESS read-only
      STATUS     current
      DESCRIPTION
             "This attribute is used to configure the name on a 
              signature."
      ::= { bsnCustomSignatureEntry 2 }

bsnCustomSignatureDescription OBJECT-TYPE
      SYNTAX DisplayString (SIZE(0..100))
      MAX-ACCESS read-only
      STATUS     current
      DESCRIPTION
             "This attribute is used to configure the description of a
              signature."
      ::= { bsnCustomSignatureEntry 3 }

bsnCustomSignatureFrameType OBJECT-TYPE
      SYNTAX     INTEGER { management(0) , data (1)}
      MAX-ACCESS read-only
      STATUS     current
      DESCRIPTION
             "This attribute specifies the type of frame that needs to 
              match a signature."
      ::= { bsnCustomSignatureEntry 4 }

bsnCustomSignatureAction OBJECT-TYPE
      SYNTAX     INTEGER { none (0) , report (1), 
                           contain(2), exclude(3)}
      MAX-ACCESS read-only
      STATUS     current
      DESCRIPTION
             "This attribute specifies the action to be taken once a 
              packet is found to match a signature."
      ::= { bsnCustomSignatureEntry 5 }

bsnCustomSignatureState OBJECT-TYPE
      SYNTAX     INTEGER { disabled(0) , enabled(1)}
      MAX-ACCESS read-only
      STATUS     current
      DESCRIPTION
             "This attribute specifies the state of a signature. It is 
              used to match packets only if the state is enabled."
      ::= { bsnCustomSignatureEntry 6 }

bsnCustomSignatureFrequency OBJECT-TYPE
      SYNTAX Unsigned32(0..65535)
      MAX-ACCESS read-only
      STATUS     current
      DESCRIPTION
             "This specifies the frequency of the matching packets 
              after which the specified action is taken."
      ::= { bsnCustomSignatureEntry 7 }

bsnCustomSignatureQuietTime OBJECT-TYPE
      SYNTAX Unsigned32(0..65535)
      MAX-ACCESS read-only
      STATUS     current
      DESCRIPTION
             "This specifies the quiet time in seconds during which no
              matching packets are found after which the
             attack is considered stopped."
      ::= { bsnCustomSignatureEntry 8 }

bsnCustomSignatureVersion OBJECT-TYPE
      SYNTAX Unsigned32(0..128)
      MAX-ACCESS read-only
      STATUS     current
      DESCRIPTION
             "This specifies the signature version."
      ::= { bsnCustomSignatureEntry 9 }

bsnCustomSignatureConfigType OBJECT-TYPE
      SYNTAX     INTEGER { pattern(0) , protocol(1)}
      MAX-ACCESS read-only
      STATUS     current
      DESCRIPTION
             "This attribute specifies the type of Signature 
              configuration. It's protocol when the protocol format is
              used in the UI to configure this. Pattern is the config 
              type for all signatures in the released signature file 
              and when signatures are configured using pattern
              format. Note: the signatures will be allowed to be 
              configured in later releases."
      ::= { bsnCustomSignatureEntry 10 }

bsnCustomSignatureEnable OBJECT-TYPE
      SYNTAX     TruthValue
      MAX-ACCESS read-write
      STATUS     current
      DESCRIPTION
              "This object configures the status of a particular
              Custom signature on LWAPP APs, for use in performing
              signature analysis on the received 802.11 data and/or
              management frames.

              A value of 'true' makes the Controller send the
              'Signature Add LWAPP Message' to all the joined APs
              with the status field set to 'enable'.  This makes
              the joined APs perform signature analysis on the
              received 802.11 data and/or management frames and
              report the discrepancies observed, if any, to the
              Controller.

              A value of 'false' makes the Controller send the
              'Signature Add LWAPP Message' to all the joined APs
              with the status field set to 'disable'.  The joined
              APs doesn't perform the signature analysis on the
              received 802.11 data and/or management frames for
              this particular signature, till the signature is
              enabled. "
      DEFVAL  { false }
      ::= { bsnCustomSignatureEntry 11 }

bsnCustomSignatureMacInfo OBJECT-TYPE
        SYNTAX     BsnTxtSignatureMacInfo
        MAX-ACCESS read-only
        STATUS     current
        DESCRIPTION
                "This object defines the pattern followed by the
                LWAPP APs to perform signature analysis with this
                Custom signature and report the results to the
                Controller. "
      ::= { bsnCustomSignatureEntry 12 }

bsnCustomSignatureMacFreq OBJECT-TYPE
        SYNTAX     Unsigned32(0..65535)
        MAX-ACCESS read-only
        STATUS     current
        DESCRIPTION
                "This object specifies the frequency of matching
                packets from a particular source after which the
                specified action is taken. "
        ::= { bsnCustomSignatureEntry 13 }

bsnCustomSignatureRowStatus  OBJECT-TYPE
      SYNTAX RowStatus
      MAX-ACCESS read-only
      STATUS current
      DESCRIPTION
      "Row Status for creation/deletion. Signature will allowed to be
       created, deleted and edited in later releases."
      ::= { bsnCustomSignatureEntry 20 }


--*******************************************************************
-- *  Packet Matching Patterns of a Custom Signature
--*******************************************************************

bsnCustomSignaturePatternTable OBJECT-TYPE
      SYNTAX     SEQUENCE OF BsnCustomSignaturePatternEntry
      MAX-ACCESS not-accessible
      STATUS     current
      DESCRIPTION
            "The table listing the matching patterns specified for a 
             Standard Signature. These are instrumental in
             matching the signature with a packet. A maximum of 5 
             patterns may be specifed for a signature.
             These are used for matching in the order of their index."
      ::= { bsnSignatureConfig 4 }

bsnCustomSignaturePatternEntry OBJECT-TYPE
      SYNTAX     BsnCustomSignaturePatternEntry
      MAX-ACCESS not-accessible
      STATUS     current
      DESCRIPTION
            "...."
      INDEX      { bsnCustomSignaturePrecedence, 
                   bsnCustomSignaturePatternIndex }
      ::= { bsnCustomSignaturePatternTable 1 }

BsnCustomSignaturePatternEntry ::= SEQUENCE {
          bsnCustomSignaturePatternIndex                Unsigned32,
          bsnCustomSignaturePatternOffset               Unsigned32,
          bsnCustomSignaturePatternString               DisplayString,
          bsnCustomSignaturePatternMask                 DisplayString,
          bsnCustomSignaturePatternRowStatus            RowStatus,
          bsnCustomSignaturePatternOffSetStart          
                                       BsnSignaturePatternOffSetStart
}

bsnCustomSignaturePatternIndex OBJECT-TYPE
      SYNTAX Unsigned32(1..5)
      MAX-ACCESS read-only
      STATUS     current
      DESCRIPTION
             "Index of the pattern. This specifies the order in which 
              the pattern is checked against the packet contents."
      ::= { bsnCustomSignaturePatternEntry 1 }

bsnCustomSignaturePatternOffset OBJECT-TYPE
      SYNTAX Unsigned32(0..128)
      MAX-ACCESS read-only
      STATUS     current
      DESCRIPTION
             "Offset from the start of the packet where the AP looks 
              for a match to the pattern."
      ::= { bsnCustomSignaturePatternEntry 2 }

bsnCustomSignaturePatternString OBJECT-TYPE
      SYNTAX DisplayString (SIZE(0..62))
      MAX-ACCESS read-only
      STATUS     current
      DESCRIPTION
             "This is the pattern string that the AP uses to match at 
              the offset. Example: 0x616c7068615f3178"
      ::= { bsnCustomSignaturePatternEntry 3 }

bsnCustomSignaturePatternMask OBJECT-TYPE
      SYNTAX DisplayString (SIZE(0..62))
      MAX-ACCESS read-only
      STATUS     current
      DESCRIPTION
             "This is the pattern mask. This is the bit mask that the 
              AP uses to mask out the bits in the packet at the given 
              offset. Example: 0xffffffffffffffff"
      ::= { bsnCustomSignaturePatternEntry 4 }

bsnCustomSignaturePatternOffSetStart OBJECT-TYPE
        SYNTAX     BsnSignaturePatternOffSetStart
        MAX-ACCESS read-only
        STATUS     current
        DESCRIPTION
                "This object indicates how an offset should be applied
                while doing signature analysis for QOS and non-QOS
                data frames with this custom signature. "
      ::= { bsnCustomSignaturePatternEntry 5 }

bsnCustomSignaturePatternRowStatus  OBJECT-TYPE
      SYNTAX RowStatus
      MAX-ACCESS read-only
      STATUS current
      DESCRIPTION
      " Row Status for creation/deletion. Signature Pattern will 
        allowed to be created, deleted and edited in later releases."
      ::= { bsnCustomSignaturePatternEntry 15 }


-- ********************************************************************
-- *  Global parameter for Signature Check enable/disable
-- ********************************************************************

 bsnSignatureCheckState OBJECT-TYPE
        SYNTAX INTEGER { disable(0), enable(1)}
        MAX-ACCESS read-write
        STATUS current
        DESCRIPTION
        "This flag should be enabled to enforce check of all standard 
         and custom signatures.  If disabled, there will be no check 
         for signatures, both custom and standard, by the switch."
    DEFVAL { disable }
        ::= { bsnSignatureConfig 5 }

  

-- ********************************************************************
-- *  Global RF ID Tag configuration
-- ********************************************************************

 bsnRfIdTagConfig OBJECT IDENTIFIER ::= {bsnGlobalDot11Config 43}

bsnRfIdTagStatus OBJECT-TYPE
        SYNTAX INTEGER { disable(0), enable(1)}
        MAX-ACCESS read-write
        STATUS current
        DESCRIPTION
        "This flag should be turned on to allow the switch to collect 
         data for tags."
        ::= { bsnRfIdTagConfig 1 }

bsnRfIdTagDataTimeout OBJECT-TYPE
        SYNTAX Unsigned32(60..7200)
        MAX-ACCESS read-write
        STATUS current
        DESCRIPTION
        "This is the number of seconds after which the tag data is 
         deleted by the switch from its database if it didn't hear 
         from the tag again."
        ::= { bsnRfIdTagConfig 2 }

bsnRfIdTagAutoTimeoutStatus OBJECT-TYPE
        SYNTAX INTEGER { disable(0), enable(1)}
        MAX-ACCESS read-write
        STATUS current
        DESCRIPTION
        "This flag should be turned on to allow auto deletion of tag 
         data in the switch after expiration of Tag Data Timeout"
        ::= { bsnRfIdTagConfig 3 }


--********************************************************************
-- *  Global AP Neighbor Authentication configuration
--********************************************************************

bsnAPNeighborAuthConfig OBJECT IDENTIFIER ::= {bsnGlobalDot11Config 44}

bsnAPNeighborAuthStatus OBJECT-TYPE
        SYNTAX INTEGER { disable(0), enable(1)}
        MAX-ACCESS read-write
        STATUS current
        DESCRIPTION
        "This flag should be turned on to allow the AP-Neighbor 
         Authentication feature."
        ::= { bsnAPNeighborAuthConfig 1 }

bsnAPNeighborAuthAlarmThreshold OBJECT-TYPE
        SYNTAX INTEGER(1..255)
        MAX-ACCESS read-write
        STATUS current
        DESCRIPTION
        "Authentication alarm trigger threshold."
        ::= { bsnAPNeighborAuthConfig 2 }


bsnRFNetworkName OBJECT-TYPE
        SYNTAX OCTET STRING (SIZE(0..19))
        MAX-ACCESS read-write
        STATUS current
        DESCRIPTION
        "RF Network Group Name to which this Airespace Switch belongs.
         Airespace Switches on a network form a RF Network Group as 
         well as a Mobility Group. RF Network Groups does the channel 
         and power management of AP while Mobility Group does load 
         balancing and hand off for clients."
    ::= { bsnGlobalDot11Config 45 }


bsnFastSSIDChangeFeature OBJECT-TYPE
        SYNTAX INTEGER { disable(0), enable(1)}
        MAX-ACCESS read-write
        STATUS current
        DESCRIPTION 
        "Configures Fast SSID changing feature for mobile-stations. 
         When enabled, permits mobile-stations to change SSIDs without 
         having to block and wait for SSID-cleanup on the switch to 
         occur."
    ::= { bsnGlobalDot11Config 46 }
    
--********************************************************************
--*  Mesh AP Configuration
--********************************************************************

bsnBridgingPolicyConfig OBJECT IDENTIFIER ::= {bsnGlobalDot11Config 47}

bsnBridgingZeroTouchConfig OBJECT-TYPE
    SYNTAX INTEGER { disable(0), enable(1) }
    MAX-ACCESS read-write
   STATUS current
    DESCRIPTION 
    "If enabled, allows new bridging APs to negotiate with the 
     switch to acquire the shared secret key."
    DEFVAL { disable }
    ::= { bsnBridgingPolicyConfig 1 }

bsnBridgingSharedSecretKey OBJECT-TYPE
    SYNTAX OCTET STRING (SIZE(0..32))
    MAX-ACCESS read-write
    STATUS current
    DESCRIPTION 
    "Key that is used to negotiate a secure LWAPP connection
     between a switch and a bridging or mesh AP."
   ::= { bsnBridgingPolicyConfig 2 }


-- ********************************************************************
-- *  BSN Global 802.11a and 802.11b Parameters
-- ********************************************************************


    bsnGlobalDot11b OBJECT IDENTIFIER ::= {bsnGlobalDot11 2}

    bsnGlobalDot11a OBJECT IDENTIFIER ::= {bsnGlobalDot11 3}

    bsnGlobalDot11h OBJECT IDENTIFIER ::= {bsnGlobalDot11 4}


-- ********************************************************************
-- *  BSN Global Parameters for Dot11B
-- ********************************************************************

bsnGlobalDot11bConfig OBJECT IDENTIFIER ::= { bsnGlobalDot11b 1 }

bsnGlobalDot11bNetworkStatus OBJECT-TYPE
    SYNTAX INTEGER {disable(0),enable(1)}
    MAX-ACCESS read-write
    STATUS current
    DESCRIPTION
    "802.11b Network Admin Status."
   ::= {bsnGlobalDot11bConfig 1}

bsnGlobalDot11bBeaconPeriod OBJECT-TYPE
    SYNTAX INTEGER (20..1000)
    MAX-ACCESS read-write
    STATUS current
    DESCRIPTION
        "This attribute shall specify the number of TU that a
     AP Radio shall use for scheduling Beacon tranmissions.
     This value is transmitted in Beacon and Probe Response
     frames."
   ::= {bsnGlobalDot11bConfig 2}


bsnGlobalDot11bDynamicChannelAssignment OBJECT-TYPE
    SYNTAX INTEGER { automatic (1),
                     runOnce (2), static (3) }
    MAX-ACCESS read-write
    STATUS current
    DESCRIPTION
        "Dynamic channel assignment(DCA) has three modes. When the mode
    is auto, the channel assignment will be periodically updated for
    all Airespace APs that permit this operation. When the DCA is 
    runOnce, channel assignments are updated based on the UPDATE_CMD 
    received from the management. When the DCA is static, no dynamic 
    channel assignments occurs and value are set to their global 
    default.  Default is auto."
   DEFVAL { automatic }
   ::= {bsnGlobalDot11bConfig 3}

bsnGlobalDot11bCurrentChannel OBJECT-TYPE
        SYNTAX INTEGER (1..14)
        MAX-ACCESS read-write
        STATUS current
        DESCRIPTION
            "The current operating frequency channel of the DSSS
        PHY. Valid channel numbers are as defined in 15.4.6.2.
        This attribute will be read-only if 
        bsnAPIfPhyChannelAutomaticOn is true."
    ::= { bsnGlobalDot11bConfig 4 }

bsnGlobalDot11bDynamicChannelUpdateInterval OBJECT-TYPE
    SYNTAX Unsigned32
    MAX-ACCESS read-only
    STATUS current
    DESCRIPTION
        "When Channel dynamic alogirthm is running, this interval (in 
         secs) specifies how often Channel assignement updates are 
         attempted on an Airespace AP. NOTE: hysteresis is built into 
         the algorithms so we will not have uproductive changes
         occuring. Default value is 600 secs"
   DEFVAL { 600 }
   ::= {bsnGlobalDot11bConfig 5}

bsnGlobalDot11bInputsForDCA OBJECT-TYPE
    SYNTAX  Unsigned32
    MAX-ACCESS read-write
    STATUS current
    DESCRIPTION
         "This attribute is a bit mask specifying what to include in
         DCA optimization.Below is a list of parameters and their 
         corresponding bits identifiers.
                options                         bit
                --------------------------------------
                none                             0
                SIGNAL STRENGTH                  1
                NOISE                            2
                FOREIGN INTERFERENCE             4
                LOAD                             8
         Default value is 15( all bits on).
         "
   DEFVAL { 15 }
   ::= {bsnGlobalDot11bConfig 6}


bsnGlobalDot11bChannelUpdateCmdInvoke OBJECT-TYPE
    SYNTAX INTEGER { default (0), activate (1) }
    MAX-ACCESS read-write
    STATUS current
    DESCRIPTION
        "When set to activate this starts a DCA calculation regardless
         of the dynamic update interval. This command should be invoke
         on Group Leader Airespace Switch.Invoking on a Airespace 
         Switch which is not a Group leader has no effect."
    ::= {  bsnGlobalDot11bConfig 7 }

bsnGlobalDot11bChannelUpdateCmdStatus OBJECT-TYPE
    SYNTAX Integer32
    MAX-ACCESS read-only
    STATUS current
    DESCRIPTION
        "After setting bsnGlobalDot11bChannelUpdateCmdInvoke to 
         activate, the result of action can be monitored from here. It
         takes 5 minutes for the command to complete."
    ::= {  bsnGlobalDot11bConfig 8 }


bsnGlobalDot11bDynamicTransmitPowerControl OBJECT-TYPE
    SYNTAX INTEGER { automatic (1), runOnce (2), static (3) }
    MAX-ACCESS read-write
    STATUS current
    DESCRIPTION
        "Dynamic transmit power (DTP) has three modes. When the mode
         is auto, the transmit power of each Airespace AP will be 
         periodically updated for all Airespace APs that permit this 
         operation. When the DTP is runOnce,transmit power update will
         occur based on the UPDATE_CMD received from the management. 
         When the DTP is static, no dynamic transmit power updates 
         occur and their global defaults are used.  Default is auto."
   DEFVAL { automatic }
   ::= {bsnGlobalDot11bConfig 9}

bsnGlobalDot11bDynamicTxPowerControlInterval OBJECT-TYPE
    SYNTAX Unsigned32
    MAX-ACCESS read-only
    STATUS current
    DESCRIPTION
        "When Tx PowerControl dynamic alogirthm is running, this 
         interval(in secs) specifies how often TxPower control updates
         are attempted on an Airespace AP. NOTE: hysteresis is
         build into the algorithms so we will not have uproductive 
         changes occuring. Default value is 600 secs"
   DEFVAL { 600 }
   ::= {bsnGlobalDot11bConfig 10}

bsnGlobalDot11bCurrentTxPowerLevel OBJECT-TYPE
        SYNTAX INTEGER (1..5)
        MAX-ACCESS read-write
        STATUS current
        DESCRIPTION
            "The TxPowerLevel N currently being used to transmit data.
            Some PHYs also use this value to determine the receiver
            sensitivity requirements for CCA."
    ::= { bsnGlobalDot11bConfig 11 }

bsnGlobalDot11bInputsForDTP OBJECT-TYPE
    SYNTAX  Unsigned32
    MAX-ACCESS read-write
    STATUS current
    DESCRIPTION
         "This attribute is a bit mask specifying what to include in
         DCA optimization.Below is a list of parameters and their 
         corresponding bits identifiers.
                options                         bit
                --------------------------------------
                none                             0
                LOAD                             1
                SIGNAL STRENGTH                  2
                FOREIGN INTERFERENCE             4
                NOISE                            8
         Default value is 15( all bits on).
         "
   DEFVAL { 15 }
   ::= {bsnGlobalDot11bConfig 12}


bsnGlobalDot11bPowerUpdateCmdInvoke OBJECT-TYPE
    SYNTAX INTEGER { default (0), activate (1) }
    MAX-ACCESS read-write
    STATUS current
    DESCRIPTION
        "When set to activate this starts a DTP calculation regardless
         of the dynamic update interval. This command should be 
         invoke on Group Leader Airespace Switch.Invoking on a 
         Airespace Switch which is not a Group leader has no effect."
    ::= {  bsnGlobalDot11bConfig 13 }

bsnGlobalDot11bPowerUpdateCmdStatus OBJECT-TYPE
    SYNTAX Integer32
    MAX-ACCESS read-only
    STATUS current
    DESCRIPTION
        "After setting bsnGlobalDot11aChannelUpdateCmdInvoke to 
         activate, the result of action can be monitored from here. It
         takes 5 minutes for the command to complete.
         "
    ::= {  bsnGlobalDot11bConfig 14 }


bsnGlobalDot11bDataRate1Mhz OBJECT-TYPE
    SYNTAX INTEGER {supported(1),mandatory(2),disabled(0)}
    MAX-ACCESS read-write
    STATUS current
    DESCRIPTION
    " Specify if this rate is supported or mandatory or disabled"
    ::= { bsnGlobalDot11bConfig 15 }

bsnGlobalDot11bDataRate2Mhz OBJECT-TYPE
    SYNTAX INTEGER {supported(1),mandatory(2),disabled(0)}
    MAX-ACCESS read-write
    STATUS current
    DESCRIPTION
    " Specify if this rate is supported or mandatory or disabled"
    ::= { bsnGlobalDot11bConfig 16 }

bsnGlobalDot11bDataRate5AndHalfMhz OBJECT-TYPE
    SYNTAX INTEGER {supported(1),mandatory(2),disabled(0)}
    MAX-ACCESS read-write
    STATUS current
    DESCRIPTION
    " Specify if this rate is supported or mandatory or disabled"
    ::= { bsnGlobalDot11bConfig 17 }

bsnGlobalDot11bDataRate11Mhz OBJECT-TYPE
    SYNTAX INTEGER {supported(1),mandatory(2),disabled(0)}
    MAX-ACCESS read-write
    STATUS current
    DESCRIPTION
    " Specify if this rate is supported or mandatory or disabled"
    ::= { bsnGlobalDot11bConfig 18 }

bsnGlobalDot11bShortPreamble OBJECT-TYPE
    SYNTAX INTEGER {disable(0),enable(1)}
    MAX-ACCESS read-write
    STATUS current
    DESCRIPTION
    "802.11b Short Preamble."
   ::= {bsnGlobalDot11bConfig 19}

bsnGlobalDot11bDot11gSupport OBJECT-TYPE
    SYNTAX INTEGER {disable(0),enable(1)}
    MAX-ACCESS read-write
    STATUS current
    DESCRIPTION
    "This attribute is enabled to also support 802.11g protocol on the
     802.11b network. Enabling 802.11g allows additional data 
     rates: 6, 9, 12, 18, 24, 36, 48, 54 Mbps."
   ::= {bsnGlobalDot11bConfig 20}

bsnGlobalDot11bDataRate6Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 21 }

bsnGlobalDot11bDataRate9Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 22 }

bsnGlobalDot11bDataRate12Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 23 }

bsnGlobalDot11bDataRate18Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 24 }

bsnGlobalDot11bDataRate24Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 25 }

bsnGlobalDot11bDataRate36Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 26 }

bsnGlobalDot11bDataRate48Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 27 }

bsnGlobalDot11bDataRate54Mhz OBJECT-TYPE
    SYNTAX INTEGER {supported(1),mandatory(2),disabled(0)}
    MAX-ACCESS read-write
    STATUS current
    DESCRIPTION
    "Specify if this rate is supported or mandatory or disabled. This 
     is configurable only if 802.11g support is enabled."
    ::= { bsnGlobalDot11bConfig 28 }

bsnGlobalDot11bPicoCellMode OBJECT-TYPE
    SYNTAX INTEGER {enable(1),disable(0)}
    MAX-ACCESS read-write
    STATUS current
    DESCRIPTION
    "Configures the 802.11b pico-cell mode. This cannot be enabled 
     when the Fast Roaming Mode is enabled."
    ::= { bsnGlobalDot11bConfig 29 }

bsnGlobalDot11bFastRoamingMode OBJECT-TYPE
    SYNTAX INTEGER {disable(0),enable(1)}
    MAX-ACCESS read-write
    STATUS current
    DESCRIPTION
    "Configures the 802.11b fast-roaming mode. This cannot be enabled 
     when the Pico Cell Mode is enabled."
    ::= { bsnGlobalDot11bConfig 30 }

bsnGlobalDot11bFastRoamingVoipMinRate OBJECT-TYPE
    SYNTAX INTEGER {undefined(0),rate1Mbps(1),
                   rate2Mbps(2),rate5andHalfMbps(3),
                   rate11Mbps(4)}
    MAX-ACCESS read-write
    STATUS current
    DESCRIPTION
    "Configures the minimum transmission rate allowed for VoIP on any 
     802.11b radio."
    ::= { bsnGlobalDot11bConfig 31 }

bsnGlobalDot11bFastRoamingVoipPercentage OBJECT-TYPE
    SYNTAX INTEGER {zero(1),twentyfive(2),
                   fifty(3),seventyfive(4),
                   hundred(5)}
    MAX-ACCESS read-write
    STATUS current
    DESCRIPTION
    "Configures the percentage of effective bandwidth for the minimum 
     rate reserved for VoIP."
    ::= { bsnGlobalDot11bConfig 32 }

bsnGlobalDot11b80211eMaxBandwidth OBJECT-TYPE
    SYNTAX INTEGER (0..100)
    MAX-ACCESS read-write
    STATUS current
    DESCRIPTION
    "This represents the maximum bandwidth allocated to 802.11e 
     clients.  It is expressed as percentage of the total bandwidth of
     802.11b network.  The value of this attribute can vary from 0 to 
     100."
   ::= {bsnGlobalDot11bConfig 33}

bsnGlobalDot11bDTPCSupport OBJECT-TYPE
    SYNTAX INTEGER {disable(0),enable(1)}
    MAX-ACCESS read-write
    STATUS current
    DESCRIPTION
    "This attribute may be used to enable the DTPC support on all 
     802.11b/g radios. DTPC or Dynamic Transmit Power Control support 
     means that the radio's transmit power will be advertised in the 
     beacons and probe responses."
    ::= { bsnGlobalDot11bConfig 34 }
    
--********************************************************************
--*  Begin of bsnGlobalDot11bPhy
--********************************************************************

bsnGlobalDot11bPhy OBJECT IDENTIFIER ::= { bsnGlobalDot11b 2 }

bsnGlobalDot11bMediumOccupancyLimit OBJECT-TYPE
    SYNTAX INTEGER (0..1000)
    MAX-ACCESS read-only
    STATUS current
    DESCRIPTION
        "This attribute shall indicate the maximum amount of time,
         in TU, that a point coordinator may control the usage of
         the wireless medium without relinquishing control for long
         enough to allow at least one instance of DCF access to the
         medium.  The default value of this attribute shall be 100,
         and the maximum value shall be 1000."
    ::= { bsnGlobalDot11bPhy 1 }

bsnGlobalDot11bCFPPeriod OBJECT-TYPE
    SYNTAX INTEGER (0..255)
    MAX-ACCESS read-only
    STATUS current
    DESCRIPTION
        "The attribute shall describe the number of DTIM intervals
         between the start of CFPs.  It is modified by
         MLME-START.request primitive."
    ::= { bsnGlobalDot11bPhy 2 }

bsnGlobalDot11bCFPMaxDuration OBJECT-TYPE
    SYNTAX INTEGER (0..65535)
    MAX-ACCESS read-only
    STATUS current
    DESCRIPTION
        "The attribute shall describe the maximum duration of the CFP
         in TU that may be generated by the PCF. It is modified by
         MLME-START.request primitive."
    ::= { bsnGlobalDot11bPhy 3 }

bsnGlobalDot11bCFPollable OBJECT-TYPE
    SYNTAX INTEGER {no(0),yes(1)}
    MAX-ACCESS read-only
    STATUS current
    DESCRIPTION
           "When this attribute is true, it shall indicate that the STA
           is able to respond to a CF-Poll with a data frame within a
           SIFS time. This attribute shall be false if the STA is not
           able to respond to a CF-Poll with a data frame within a SIFS
           time."
    ::= { bsnGlobalDot11bPhy 5 }

bsnGlobalDot11bCFPollRequest OBJECT-TYPE
    SYNTAX INTEGER {no(0),yes(1)}
    MAX-ACCESS read-only
    STATUS current
    DESCRIPTION
            "Specifies wheather CFP"
    ::= { bsnGlobalDot11bPhy 6 }

bsnGlobalDot11bDTIMPeriod OBJECT-TYPE
    SYNTAX INTEGER(1..255)
    MAX-ACCESS read-write
    STATUS current
    DESCRIPTION
        "This attribute shall specify the number of beacon
        intervals that shall elapse between transmission of
        Beacons frames containing a TIM element whose DTIM
        Count field is 0. This value is transmitted in
        the DTIM Period field of Beacon frames."
    ::= { bsnGlobalDot11bPhy 7 }

bsnGlobalDot11bMaximumTransmitPowerLevel OBJECT-TYPE
        SYNTAX Integer32
        MAX-ACCESS read-only
        STATUS current
        DESCRIPTION
            "This attribute shall indicate the maximum transmit power,
             in dBm, allowed in the subband for the associated domain 
             country string.  The default value of this attribute shall
             be zero."
        ::= { bsnGlobalDot11bPhy 8 }

bsnGlobalDot11bFirstChannelNumber OBJECT-TYPE
        SYNTAX Integer32
        MAX-ACCESS read-only
        STATUS current
        DESCRIPTION
            "This attribute shall indicate the value of the lowest 
             channel number in the subband for the associated domain 
             country string. The default value of this attribute shall
             be zero."
        ::= { bsnGlobalDot11bPhy 9 }

bsnGlobalDot11bNumberofChannels OBJECT-TYPE
        SYNTAX Integer32
        MAX-ACCESS read-only
        STATUS current
        DESCRIPTION
              "This attribute shall indicate the value of the total 
               number of channels allowed in the subband for the 
               associated domain country string. The default value of 
               this attribute shall be zero."
        ::= { bsnGlobalDot11bPhy 10 }

bsnGlobalDot11bRTSThreshold OBJECT-TYPE
   SYNTAX INTEGER (0..2347)
   MAX-ACCESS read-only
   STATUS current
   DESCRIPTION
        "This attribute shall indicate the number of octets in an MPDU,
        below which an RTS/CTS handshake shall not be performed. An
        RTS/CTS handshake shall be performed at the beginning of any
        frame exchange sequence where the MPDU is of type Data or
        Management, the MPDU has an individual address in the Address1
        field, and the length of the MPDU is greater than
        this threshold. (For additional details, refer to Table 21 in
        9.7.) Setting this attribute to be larger than the maximum
        MSDU size shall have the effect of turning off the RTS/CTS
        handshake for frames of Data or Management type transmitted by
        this STA. Setting this attribute to zero shall have the effect
        of turning on the RTS/CTS handshake for all frames of Data or
        Management type transmitted by this STA. The default value of
        this attribute shall be 2347."
    ::= { bsnGlobalDot11bPhy 11 }

bsnGlobalDot11bShortRetryLimit OBJECT-TYPE
    SYNTAX INTEGER (1..255)
    MAX-ACCESS read-only
    STATUS current
    DESCRIPTION
        "This attribute shall indicate the maximum number of
        transmission attempts of a frame, the length of which is less
        than or equal to bsnGlobalDot11RTSThreshold, that shall be made
        before a failure condition is indicated. The default value of 
        this attribute shall be 7."
    ::= { bsnGlobalDot11bPhy 12 }

bsnGlobalDot11bLongRetryLimit OBJECT-TYPE
    SYNTAX INTEGER (1..255)
    MAX-ACCESS read-only
    STATUS current
    DESCRIPTION
      "This attribute shall indicate the maximum number of
      transmission attempts of a frame, the length of which is
      greater than bsnGlobalDot11RTSThreshold, that shall be made 
      before a failure condition is indicated. The default value of 
      this attribute shall be 4."
    ::= { bsnGlobalDot11bPhy 13 }

bsnGlobalDot11bFragmentationThreshold OBJECT-TYPE
        SYNTAX INTEGER (256..2346)
        MAX-ACCESS read-write
        STATUS current
        DESCRIPTION
        "This attribute shall specify the current maximum size, in
        octets, of the MPDU that may be delivered to the PHY. An MSDU
        shall be broken into fragments if its size exceeds the value
        of this attribute after adding MAC headers and trailers. An 
        MSDU or MMPDU shall be fragmented when the resulting frame has 
        individual address in the Address1 field, and the length of the
        frame is larger than this threshold. The default value for this
        attribute shall be the lesser of 2346 or the aMPDUMaxLength of
        the attached PHY and shall never exceed the lesser of 2346 or
        the  aMPDUMaxLength of the attached PHY. The value of this
        attribute shall never be less than 256. "
    ::= { bsnGlobalDot11bPhy 14 }

bsnGlobalDot11bMaxTransmitMSDULifetime OBJECT-TYPE
        SYNTAX Unsigned32 (1..4294967295)
        MAX-ACCESS read-only
        STATUS current
        DESCRIPTION
         "The MaxTransmitMSDULifetime shall be the elapsed time in TU,
         after the initial transmission of an MSDU, after which further
         attempts to transmit the MSDU shall be terminated. The default
         value of this attribute shall be 512."
    ::= { bsnGlobalDot11bPhy 15 }

bsnGlobalDot11bMaxReceiveLifetime OBJECT-TYPE
        SYNTAX Unsigned32 (1..4294967295)
        MAX-ACCESS read-only
        STATUS current
        DESCRIPTION
            "The MaxReceiveLifetime shall be the elapsed time in TU,
            after the initial reception of a fragmented MMPDU or MSDU,
            after which further attempts to reassemble the MMPDU or
            MSDU shall be terminated. The default value shall be
            512."
    ::= { bsnGlobalDot11bPhy 16 }

bsnGlobalDot11bEDThreshold OBJECT-TYPE
        SYNTAX Integer32
        MAX-ACCESS read-only
        STATUS current
        DESCRIPTION
            "The current Energy Detect Threshold being used by the 
             DSSS PHY."
    ::= { bsnGlobalDot11bPhy 17 }

bsnGlobalDot11bChannelAgilityEnabled OBJECT-TYPE
     SYNTAX INTEGER {no(0),yes(1)}
     MAX-ACCESS read-only
     STATUS current
     DESCRIPTION
         "This attribute indicates that the PHY channel agility
          functionality is enabled."
    ::= { bsnGlobalDot11bPhy 18 }

bsnGlobalDot11bPBCCOptionImplemented OBJECT-TYPE
     SYNTAX INTEGER {no(0),yes(1)}
     MAX-ACCESS read-only
     STATUS current
     DESCRIPTION
             "This attribute, when true, shall indicate that the PBCC
             modulation option as defined in subclause 18.4.6.6 is
             implemented.  The default value of this attribute shall
             be false."
    ::= { bsnGlobalDot11bPhy 19 }

bsnGlobalDot11bShortPreambleOptionImplemented OBJECT-TYPE
     SYNTAX INTEGER {no(0),yes(1)}
     MAX-ACCESS read-only
     STATUS current
     DESCRIPTION
             "This attribute, when true, shall indicate that the
              short preamble option as defined in subclause 18.2.2.2
              is implemented.  The default value of this attribute
              shall be false."
    ::= { bsnGlobalDot11bPhy 20 }

 
-- ********************************************************************
-- *  BSN Global Parameters for Dot11A
-- ********************************************************************

bsnGlobalDot11aConfig OBJECT IDENTIFIER ::= {bsnGlobalDot11a 1}

bsnGlobalDot11aNetworkStatus OBJECT-TYPE
    SYNTAX INTEGER {disable(0),enable(1)}
    MAX-ACCESS read-write
    STATUS current
    DESCRIPTION
    "Dot11a Network Status"
   ::= {bsnGlobalDot11aConfig 1}

bsnGlobalDot11aLowBandNetwork OBJECT-TYPE
    SYNTAX INTEGER {disable(0),enable(1)}
    MAX-ACCESS read-only
    STATUS current
    DESCRIPTION
    "Dot11a Low Band Network Status"
   ::= {bsnGlobalDot11aConfig 2}

bsnGlobalDot11aMediumBandNetwork OBJECT-TYPE
    SYNTAX INTEGER {disable(0),enable(1)}
    MAX-ACCESS read-only
    STATUS current
    DESCRIPTION
    "Dot11a Mid Band Network Status"
   ::= {bsnGlobalDot11aConfig 3}

bsnGlobalDot11aHighBandNetwork OBJECT-TYPE
    SYNTAX INTEGER {disable(0),enable(1)}
    MAX-ACCESS read-only
    STATUS current
    DESCRIPTION
    "Dot11a High Band Network Status"
   ::= {bsnGlobalDot11aConfig 4}

bsnGlobalDot11aBeaconPeriod OBJECT-TYPE
    SYNTAX INTEGER (20..1000)
    MAX-ACCESS read-write
    STATUS current
    DESCRIPTION
        "This attribute shall specify the number of TU that a
     AP Radio shall use for scheduling Beacon tranmissions.
     This value is transmitted in Beacon and Probe Response 
     frames."
   ::= {bsnGlobalDot11aConfig 5}

bsnGlobalDot11aDynamicChannelAssignment OBJECT-TYPE
    SYNTAX INTEGER { automatic (1), runOnce (2), static (3) }
    MAX-ACCESS read-write
    STATUS current
    DESCRIPTION
        "Dynamic channel assignment(DCA) has three modes. When the mode
         is auto, the channel assignment will be periodically updated 
         for all Airespace APs that permit this operation. When the DCA
         is runOnce, channel assignments are updated based on the 
         UPDATE_CMD received from the management. When the DCA is 
         static, no dynamic channel assignments occurs and value are 
         set to their global default.  Default is auto."
   DEFVAL { automatic }
   ::= {bsnGlobalDot11aConfig 6}

bsnGlobalDot11aCurrentChannel OBJECT-TYPE
     SYNTAX INTEGER (0..99)
     MAX-ACCESS read-write
     STATUS current
     DESCRIPTION
         "The number of the current operating frequency channel of the
         OFDM PHY."
    ::= { bsnGlobalDot11aConfig 7 }

bsnGlobalDot11aDynamicChannelUpdateInterval OBJECT-TYPE
    SYNTAX Unsigned32
    MAX-ACCESS read-only
    STATUS current
    DESCRIPTION
        "When Channel dynamic alogirthm is running, this interval(in 
         secs) specifies how often Channel assignement updates are 
         attempted on an Airespace AP. NOTE: hysteresis is
         build into the algorithms so we will not have uproductive 
         changes occuring. Default value is 600 secs"
   DEFVAL { 600 }
   ::= {bsnGlobalDot11aConfig 8}

bsnGlobalDot11aInputsForDCA OBJECT-TYPE
    SYNTAX  Unsigned32
    MAX-ACCESS read-write
    STATUS current
    DESCRIPTION
         "This attribute is a bit mask specifying what to include in
         DCA optimization.Below is a list of parameters and their 
         corresponding bits identifiers.
                options                         bit
                --------------------------------------
                none                             0
                SIGNAL STRENGTH                  1
                NOISE                            2
                FOREIGN INTERFERENCE             4
                LOAD                             8
         Default value is 15( all bits on).
         "
   DEFVAL { 15 }
   ::= {bsnGlobalDot11aConfig 9}

bsnGlobalDot11aChannelUpdateCmdInvoke OBJECT-TYPE
    SYNTAX INTEGER { default (0), activate (1) }
    MAX-ACCESS read-write
    STATUS current
    DESCRIPTION
        "When set to activate this starts a DCA calculation regardless
         of the dynamic update interval. This command should be invoke
         on Group Leader Airespace Switch.Invoking on a Airespace 
         Switch which is not a Group leader has no effect."
    ::= {  bsnGlobalDot11aConfig 10 }

bsnGlobalDot11aChannelUpdateCmdStatus OBJECT-TYPE
    SYNTAX Integer32
    MAX-ACCESS read-only
    STATUS current
    DESCRIPTION
        "After setting bsnGlobalDot11aChannelUpdateCmdInvoke to 
         activate, the result of action can be monitored from here. It 
         takes 5 minutes for the command to complete.
         "
    ::= {  bsnGlobalDot11aConfig 11 }

bsnGlobalDot11aDynamicTransmitPowerControl OBJECT-TYPE
    SYNTAX INTEGER { automatic (1), runOnce (2), static (3) }
    MAX-ACCESS read-write
    STATUS current
    DESCRIPTION
        "Dynamic transmit power (DTP) has three modes. When the mode
         is auto, the transmit power of each Airespace AP will be 
         periodically updated for all Airespace APs that permit this 
         operation. When the DTP is runOnce,transmit power update will
         occur based on the UPDATE_CMD received from the management. 
         When the DTP is static, no dynamic transmit power updates 
         occur and their global defaults are used.  Default is auto."
   DEFVAL { automatic }
   ::= {bsnGlobalDot11aConfig 12}

bsnGlobalDot11aCurrentTxPowerLevel OBJECT-TYPE
        SYNTAX INTEGER (1..5)
        MAX-ACCESS read-write
        STATUS current
        DESCRIPTION
            "The TxPowerLevel N currently being used to transmit data.
            Some PHYs also use this value to determine the receiver
            sensitivity requirements for CCA."
    ::= { bsnGlobalDot11aConfig 13 }

bsnGlobalDot11aDynamicTxPowerControlInterval OBJECT-TYPE
    SYNTAX Unsigned32
    MAX-ACCESS read-only
    STATUS current
    DESCRIPTION
        "When Tx PowerControl dynamic alogirthm is running, this 
         interval(in secs) specifies how often TxPower control updates
         are attempted on an Airespace AP. NOTE: hysteresis is
         build into the algorithms so we will not have uproductive 
         changes occuring. Default value is 600 secs"
   DEFVAL { 600 }
   ::= {bsnGlobalDot11aConfig 14}

bsnGlobalDot11aInputsForDTP OBJECT-TYPE
    SYNTAX  Unsigned32
    MAX-ACCESS read-write
    STATUS current
    DESCRIPTION
         "This attribute is a bit mask specifying what to include in
         DCA optimization.Below is a list of parameters and their 
         corresponding bits identifiers.
                options                         bit
                --------------------------------------
                none                             0
                LOAD                             1
                SIGNAL STRENGTH                  2
                FOREIGN INTERFERENCE             4
                NOISE                            8
         Default value is 15( all bits on).
         "
   DEFVAL { 15 }
   ::= {bsnGlobalDot11aConfig 15}


bsnGlobalDot11aPowerUpdateCmdInvoke OBJECT-TYPE
    SYNTAX INTEGER { default (0), activate (1) }
    MAX-ACCESS read-write
    STATUS current
    DESCRIPTION
        "When set to activate this starts a DTP calculation regardless
         of the dynamic update interval. This command should be invoke
         on Group Leader Airespace Switch.Invoking on a Airespace 
         Switch which is not a Group leader has no effect."
    ::= {  bsnGlobalDot11aConfig 16 }

bsnGlobalDot11aPowerUpdateCmdStatus OBJECT-TYPE
    SYNTAX Integer32
    MAX-ACCESS read-only
    STATUS current
    DESCRIPTION
        "After setting bsnGlobalDot11aChannelUpdateCmdInvoke to 
         activate, the result of action can be monitored from here. It
         takes 5 minutes for the command to complete.
         "
    ::= {  bsnGlobalDot11aConfig 17 }

bsnGlobalDot11aDataRate6Mhz OBJECT-TYPE
    SYNTAX INTEGER {supported(1),mandatory(2),disabled(0)}
    MAX-ACCESS read-write
    STATUS current
    DESCRIPTION
    " Specify if this rate is supported or mandatory or disabled"
    ::= { bsnGlobalDot11aConfig 19 }

bsnGlobalDot11aDataRate9Mhz OBJECT-TYPE
    SYNTAX INTEGER {supported(1),mandatory(2),disabled(0)}
    MAX-ACCESS read-write
    STATUS current
    DESCRIPTION
    " Specify if this rate is supported or mandatory or disabled"
    ::= { bsnGlobalDot11aConfig 20 }

bsnGlobalDot11aDataRate12Mhz OBJECT-TYPE
    SYNTAX INTEGER {supported(1),mandatory(2),disabled(0)}
    MAX-ACCESS read-write
    STATUS current
    DESCRIPTION
    " Specify if this rate is supported or mandatory or disabled"
    ::= { bsnGlobalDot11aConfig 21 }

bsnGlobalDot11aDataRate18Mhz OBJECT-TYPE
    SYNTAX INTEGER {supported(1),mandatory(2),disabled(0)}
    MAX-ACCESS read-write
    STATUS current
    DESCRIPTION
    " Specify if this rate is supported or mandatory or disabled"
    ::= { bsnGlobalDot11aConfig 22 }

bsnGlobalDot11aDataRate24Mhz OBJECT-TYPE
    SYNTAX INTEGER {supported(1),mandatory(2),disabled(0)}
    MAX-ACCESS read-write
    STATUS current
    DESCRIPTION
    " Specify if this rate is supported or mandatory or disabled"
    ::= { bsnGlobalDot11aConfig 23 }

bsnGlobalDot11aDataRate36Mhz OBJECT-TYPE
    SYNTAX INTEGER {supported(1),mandatory(2),disabled(0)}
    MAX-ACCESS read-write
    STATUS current
    DESCRIPTION
    " Specify if this rate is supported or mandatory or disabled"
    ::= { bsnGlobalDot11aConfig 24 }

bsnGlobalDot11aDataRate48Mhz OBJECT-TYPE
    SYNTAX INTEGER {supported(1),mandatory(2),disabled(0)}
    MAX-ACCESS read-write
    STATUS current
    DESCRIPTION
    " Specify if this rate is supported or mandatory or disabled"
    ::= { bsnGlobalDot11aConfig 25 }

bsnGlobalDot11aDataRate54Mhz OBJECT-TYPE
    SYNTAX INTEGER {supported(1),mandatory(2),disabled(0)}
    MAX-ACCESS read-write
    STATUS current
    DESCRIPTION
    " Specify if this rate is supported or mandatory or disabled"
    ::= { bsnGlobalDot11aConfig 26 }

bsnGlobalDot11aPicoCellMode OBJECT-TYPE
    SYNTAX INTEGER {enable(1),disable(0)}
    MAX-ACCESS read-write
    STATUS current
    DESCRIPTION
    "Configures the 802.11a pico-cell mode. This cannot be enabled 
     when the Fast Roaming Mode is enabled."
    ::= { bsnGlobalDot11aConfig 27 }

bsnGlobalDot11aFastRoamingMode OBJECT-TYPE
    SYNTAX INTEGER {disable(0),enable(1)}
    MAX-ACCESS read-write
    STATUS current
    DESCRIPTION
    "Configures the 802.11a fast-roaming mode. This cannot be enabled 
     when the Pico Cell Mode is enabled."
    ::= { bsnGlobalDot11aConfig 28 }

bsnGlobalDot11aFastRoamingVoipMinRate OBJECT-TYPE
    SYNTAX INTEGER {undefined(0),
                   rate1Mbps(1),
                   rate2Mbps(2),
                   rate5andHalfMbps(3),
                   rate11Mbps(4)}
    MAX-ACCESS read-write
    STATUS current
    DESCRIPTION
    "Configures the minimum transmission rate allowed for VoIP on any 
     802.11a radio."
    ::= { bsnGlobalDot11aConfig 29 }

bsnGlobalDot11aFastRoamingVoipPercentage OBJECT-TYPE
    SYNTAX INTEGER {zero(1),twentyfive(2),
                   fifty(3),seventyfive(4),
                   hundred(5)}
    MAX-ACCESS read-write
    STATUS current
    DESCRIPTION
    "Configures the percentage of effective bandwidth for the minimum 
     rate reserved for VoIP."
    ::= { bsnGlobalDot11aConfig 30 }

bsnGlobalDot11a80211eMaxBandwidth OBJECT-TYPE
    SYNTAX INTEGER (0..100)
    MAX-ACCESS read-write
    STATUS current
    DESCRIPTION
        "This represents the maximum bandwidth allocated to 802.11e 
         clients.  It is expressed as percentage of the total bandwidth
         of 802.11a network.  The value of this attribute can vary from
         0 to 100."
   ::= {bsnGlobalDot11aConfig 31}

bsnGlobalDot11aDTPCSupport OBJECT-TYPE
    SYNTAX INTEGER {disable(0),enable(1)}
    MAX-ACCESS read-write
    STATUS current
    DESCRIPTION
    "This attribute may be used to enable the DTPC support on all 
     802.11a radios. DTPC or Dynamic Transmit Power Control support 
     means that the radio's transmit power will be advertised in the 
     beacons and probe responses."
    ::= { bsnGlobalDot11aConfig 32 }

-- ********************************************************************
-- *  Begin of bsnGlobalDot11aPhy
-- ********************************************************************

bsnGlobalDot11aPhy OBJECT IDENTIFIER ::= {bsnGlobalDot11a 2}


bsnGlobalDot11aMediumOccupancyLimit OBJECT-TYPE
    SYNTAX INTEGER (0..1000)
    MAX-ACCESS read-only
    STATUS current
    DESCRIPTION
        "This attribute shall indicate the maximum amount of time,
         in TU, that a point coordinator may control the usage of
         the wireless medium without relinquishing control for long
         enough to allow at least one instance of DCF access to the
         medium.  The default value of this attribute shall be 100,
         and the maximum value shall be 1000."
    ::= { bsnGlobalDot11aPhy 1 }

bsnGlobalDot11aCFPPeriod OBJECT-TYPE
    SYNTAX INTEGER (0..255)
    MAX-ACCESS read-only
    STATUS current
    DESCRIPTION
        "The attribute shall describe the number of DTIM intervals
         between the start of CFPs.  It is modified by
         MLME-START.request primitive."
    ::= { bsnGlobalDot11aPhy 2 }

bsnGlobalDot11aCFPMaxDuration OBJECT-TYPE
    SYNTAX INTEGER (0..65535)
    MAX-ACCESS read-only
    STATUS current
    DESCRIPTION
        "The attribute shall describe the maximum duration of the CFP
         in TU that may be generated by the PCF. It is modified by
         MLME-START.request primitive."
    ::= { bsnGlobalDot11aPhy 3 }

bsnGlobalDot11aCFPollable OBJECT-TYPE
    SYNTAX INTEGER {no(0),yes(1)}
    MAX-ACCESS read-only
    STATUS current
    DESCRIPTION
          "When this attribute is true, it shall indicate that the STA
           is able to respond to a CF-Poll with a data frame within a
           SIFS time. This attribute shall be false if the STA is not
           able to respond to a CF-Poll with a data frame within a SIFS
           time."
    ::= { bsnGlobalDot11aPhy 5 }

bsnGlobalDot11aCFPollRequest OBJECT-TYPE
    SYNTAX INTEGER {no(0),yes(1)}
    MAX-ACCESS read-only
    STATUS current
    DESCRIPTION
            "Specifies whether CFP"

    ::= { bsnGlobalDot11aPhy 6 }

bsnGlobalDot11aDTIMPeriod OBJECT-TYPE
    SYNTAX INTEGER(1..255)
    MAX-ACCESS read-write
    STATUS current
    DESCRIPTION
       "This attribute shall specify the number of beacon
        intervals that shall elapse between transmission of
        Beacons frames containing a TIM element whose DTIM
        Count field is 0. This value is transmitted in
        the DTIM Period field of Beacon frames."
    ::= { bsnGlobalDot11aPhy 7 }

bsnGlobalDot11aMaximumTransmitPowerLevel OBJECT-TYPE
        SYNTAX Integer32
        MAX-ACCESS read-only
        STATUS current
        DESCRIPTION
            "This attribute shall indicate the maximum transmit power,
             in dBm, allowed in the subband for the associated domain 
             country string. The default value of this attribute shall
             be zero."
        ::= { bsnGlobalDot11aPhy 8 }

bsnGlobalDot11aFirstChannelNumber OBJECT-TYPE
        SYNTAX Integer32
        MAX-ACCESS read-only
        STATUS current
        DESCRIPTION
            "This attribute shall indicate the value of the lowest 
             channel number in the subband for the associated domain 
             country string. 
             The default value of this attribute shall be zero."
        ::= { bsnGlobalDot11aPhy 9 }

bsnGlobalDot11aNumberofChannels OBJECT-TYPE
        SYNTAX Integer32
        MAX-ACCESS read-only
        STATUS current
        DESCRIPTION
              "This attribute shall indicate the value of the total 
               number of channels allowed in the subband for the 
               associated domain country string. The default value of 
               this attribute shall be zero."
        ::= { bsnGlobalDot11aPhy 10 }

bsnGlobalDot11aRTSThreshold OBJECT-TYPE
   SYNTAX INTEGER (0..2347)
   MAX-ACCESS read-only
   STATUS current
   DESCRIPTION
        "This attribute shall indicate the number of octets in an MPDU,
        below which an RTS/CTS handshake shall not be performed. An
        RTS/CTS handshake shall be performed at the beginning of any
        frame exchange sequence where the MPDU is of type Data or
        Management, the MPDU has an individual address in the Address1
        field, and the length of the MPDU is greater than
        this threshold. (For additional details, refer to Table 21 in
        9.7.) Setting this attribute to be larger than the maximum
        MSDU size shall have the effect of turning off the RTS/CTS
        handshake for frames of Data or Management type transmitted by
        this STA. Setting this attribute to zero shall have the effect
        of turning on the RTS/CTS handshake for all frames of Data or
        Management type transmitted by this STA. The default value of
        this attribute shall be 2347."
    ::= { bsnGlobalDot11aPhy 11 }

bsnGlobalDot11aShortRetryLimit OBJECT-TYPE
    SYNTAX INTEGER (1..255)
    MAX-ACCESS read-only
    STATUS current
    DESCRIPTION
        "This attribute shall indicate the maximum number of
        transmission attempts of a frame, the length of which is less
        than or equal to bsnGlobalDot11RTSThreshold, that shall be 
        made before a failure condition is indicated. The default 
        value of this attribute shall be 7."
    ::= { bsnGlobalDot11aPhy 12 }

bsnGlobalDot11aLongRetryLimit OBJECT-TYPE
    SYNTAX INTEGER (1..255)
    MAX-ACCESS read-only
    STATUS current
    DESCRIPTION
      "This attribute shall indicate the maximum number of
      transmission attempts of a frame, the length of which is
      greater than bsnGlobalDot11RTSThreshold, that shall be made 
      before a failure condition is indicated. The default value of 
      this attribute shall be 4."
    ::= { bsnGlobalDot11aPhy 13 }

bsnGlobalDot11aFragmentationThreshold OBJECT-TYPE
        SYNTAX INTEGER (256..2346)
        MAX-ACCESS read-write
        STATUS current
        DESCRIPTION
        "This attribute shall specify the current maximum size, in
        octets, of the MPDU that may be delivered to the PHY. An MSDU
        shall be broken into fragments if its size exceeds the value
        of this attribute after adding MAC headers and trailers. MSDU
        or MMPDU shall be fragmented when the resulting frame has an
        individual address in the Address1 field, and the length of the
        frame is larger than this threshold. The default value for this
        attribute shall be the lesser of 2346 or the aMPDUMaxLength of
        the attached PHY and shall never exceed the lesser of 2346 or
        the  aMPDUMaxLength of the attached PHY. The value of this
        attribute shall never be less than 256. "
    ::= { bsnGlobalDot11aPhy 14 }

bsnGlobalDot11aMaxTransmitMSDULifetime OBJECT-TYPE
        SYNTAX Unsigned32 (1..4294967295)
        MAX-ACCESS read-only
        STATUS current
        DESCRIPTION
         "The MaxTransmitMSDULifetime shall be the elapsed time in TU,
         after the initial transmission of an MSDU, after which further
         attempts to transmit the MSDU shall be terminated. The default
         value of this attribute shall be 512."
    ::= { bsnGlobalDot11aPhy 15 }

bsnGlobalDot11aMaxReceiveLifetime OBJECT-TYPE
        SYNTAX Unsigned32 (1..4294967295)
        MAX-ACCESS read-only
        STATUS current
        DESCRIPTION
            "The MaxReceiveLifetime shall be the elapsed time in TU,
            after the initial reception of a fragmented MMPDU or MSDU,
            after which further attempts to reassemble the MMPDU or
            MSDU shall be terminated. The default value shall be
            512."
    ::= { bsnGlobalDot11aPhy 16 }

bsnGlobalDot11aTIThreshold OBJECT-TYPE
    SYNTAX Integer32
    MAX-ACCESS read-only
    STATUS current
    DESCRIPTION
        "The Threshold being used to detect a busy medium (frequency).
        CCA shall report a busy medium upon detecting the RSSI above 
        this threshold."
    ::= { bsnGlobalDot11aPhy 17 }


bsnGlobalDot11aChannelAgilityEnabled OBJECT-TYPE
     SYNTAX INTEGER {no(0),yes(1)}
     MAX-ACCESS read-only
     STATUS current
     DESCRIPTION
         "This attribute indicates that the PHY channel agility
          functionality is enabled."
    ::= { bsnGlobalDot11aPhy 18 }

-- ********************************************************************
-- *  BSN Global Parameters for Dot11h
-- ********************************************************************

   bsnGlobalDot11hConfig OBJECT IDENTIFIER ::= { bsnGlobalDot11h 1 }
-- *******************************************************************
-- These global attributes are to Enable/Disable Power Control and 
-- Channel Switch for 802.11h
-- *******************************************************************

   bsnGlobalDot11hPowerConstraint  OBJECT-TYPE
      SYNTAX         INTEGER (0..30)
      UNITS          "decibels"
      MAX-ACCESS     read-write
      STATUS         current
      DESCRIPTION
              "Local maximum transmit power for a channel is defined as
               maximum transmit power level specified for the channel 
               in the Country element minus the local power constraint
               specified for the channel in the Power Constraint 
               element.The power constraint is coded as an unsigned 
               integer in units of decibels. To disable 
               power constraint set Power Constraint to 0."
      ::= { bsnGlobalDot11hConfig 1 }

    bsnGlobalDot11hChannelSwitchEnable OBJECT-TYPE
      SYNTAX INTEGER      { disable(0),enable (1)}
      MAX-ACCESS          read-write
      STATUS              current
      DESCRIPTION
               "To enable or disable  channel switch. When disabling 
                Channel Switch no need to pass mode and count "
      ::= { bsnGlobalDot11hConfig 2 }

    bsnGlobalDot11hChannelSwitchMode OBJECT-TYPE
      SYNTAX INTEGER      { disable (0), enable(1)}
      MAX-ACCESS          read-write
      STATUS              current
      DESCRIPTION
               " The Channel Switch Mode indicates any restriction on 
                 transmission until a channel switch. An Channel mode 
                 set to 1 means that the STA in a BSS to which the 
                 frame containing the element is addressed shall 
                 tranmit no further frames with in the BSS until the 
                 scheduled channel switch. A Channel switch mode set 
                 to 0 does not impose any requirement on the receiving
                 STA."
      ::= { bsnGlobalDot11hConfig 3 }

-- ********************************************************************
-- *  bsnRrm - Information about RF Groups that this Airespace Switch 
-- *  belongs to
-- ********************************************************************

bsnRrmDot11a OBJECT IDENTIFIER ::= { bsnRrm 1 }
bsnRrmDot11b OBJECT IDENTIFIER ::= { bsnRrm 2 }

-- *******************************************************************
-- * Begin of RRM dot11a Group Parameters
-- *******************************************************************
bsnRrmDot11aGroup OBJECT IDENTIFIER ::= { bsnRrmDot11a 1 }

bsnRrmDot11aGlobalAutomaticGrouping OBJECT-TYPE
    SYNTAX INTEGER { automatic (1), off (2) }
    MAX-ACCESS read-write
    STATUS current
    DESCRIPTION
        "Dynamic grouping has two modes: on and off. When the grouping
         is off, no dynamic grouping occurs. Each Airespace Switch 
         optimizes only its own Airespace APs' parameters. When 
         grouping is on, the Airespace Switches form groups and
         elect leaders to perform better dynamic parameter 
         optimization."
   DEFVAL { automatic }
   ::= {bsnRrmDot11aGroup 1}

bsnRrmDot11aGroupLeaderMacAddr OBJECT-TYPE
    SYNTAX MacAddress
    MAX-ACCESS read-only
    STATUS current
    DESCRIPTION
        "This is the MAC address of the group leader for the dot11a 
         group containing this Airespace Switch."
    ::= { bsnRrmDot11aGroup 2 }

bsnRrmIsDot11aGroupLeader OBJECT-TYPE
    SYNTAX INTEGER {no(0),yes(1)}
    MAX-ACCESS read-only
    STATUS current
    DESCRIPTION
        "If this Airespace Switch is a Dot11a Group Leader then this 
         attribute will be true else it will be false."
    ::= { bsnRrmDot11aGroup 3 }


bsnRrmDot11aGroupLastUpdateTime OBJECT-TYPE
    SYNTAX Unsigned32
    MAX-ACCESS read-only
    STATUS current
    DESCRIPTION
        "Last time the dot11a grouping was updated on this Airespace 
         Switch. This is valid only if the Airespace Switch is a 
         group leader."
    ::= { bsnRrmDot11aGroup 4 }

bsnRrmDot11aGlobalGroupInterval OBJECT-TYPE
    SYNTAX Unsigned32
    MAX-ACCESS read-only
    STATUS current
    DESCRIPTION
        "When grouping is on, this interval(in secs) represents the 
         period with which the grouping algorithm is run. Grouping 
         algorithm will also run when the group contents changes and 
         the automatic grouping is enabled. A dynamic grouping can be 
         started upon request from the system administrator. Default 
         value is 3600 secs."
   DEFVAL { 3600 }
   ::= {bsnRrmDot11aGroup 5}

-- ************************************************************
-- * Begin of bsnWras SwitchDot11aGroup Table
-- ************************************************************
bsnWrasDot11aGroupTable OBJECT-TYPE
    SYNTAX SEQUENCE OF BsnWrasDot11aGroupEntry
    MAX-ACCESS not-accessible
    STATUS current
    DESCRIPTION
       "This is a table of Airespace Switch addresses that identifies 
        the members of the Dot11a RF group containing this Airespace 
        Switch. Max size is 20 entries."
::= { bsnRrmDot11aGroup 9 }

bsnWrasDot11aGroupEntry OBJECT-TYPE
    SYNTAX BsnWrasDot11aGroupEntry
    MAX-ACCESS not-accessible
    STATUS current
    DESCRIPTION
        " ... "
    INDEX { bsnWrasDot11aPeerMacAddress }
    ::= { bsnWrasDot11aGroupTable 1 }

BsnWrasDot11aGroupEntry ::=
    SEQUENCE {
        bsnWrasDot11aPeerMacAddress       MacAddress,
        bsnWrasDot11aPeerIpAddress        IpAddress
    }

bsnWrasDot11aPeerMacAddress OBJECT-TYPE
    SYNTAX MacAddress
    MAX-ACCESS read-only
    STATUS current
    DESCRIPTION
        "The MAC address of the member Switch."
    ::= { bsnWrasDot11aGroupEntry 1 }

bsnWrasDot11aPeerIpAddress OBJECT-TYPE
    SYNTAX IpAddress
    MAX-ACCESS read-only
    STATUS current
    DESCRIPTION
        "The IP address of the Airespace Switch."
    ::= { bsnWrasDot11aGroupEntry 21 }


-- ********************************************************************
-- * Begin bsnRrmDot11aAPDefault
-- *******************************************************************
bsnRrmDot11aAPDefault OBJECT IDENTIFIER ::= { bsnRrmDot11a 6 }

-- ********************************************************************
-- * Begin bsnRrmDot11aAPProfile
-- *******************************************************************

bsnRrmDot11aForeignInterferenceThreshold OBJECT-TYPE
    SYNTAX INTEGER(0..100)
    MAX-ACCESS read-write
    STATUS current
    DESCRIPTION
      "foreign 802.11A interference threshold between 0 and 100 percent."
   ::= {bsnRrmDot11aAPDefault 1 }

bsnRrmDot11aForeignNoiseThreshold OBJECT-TYPE
    SYNTAX INTEGER(-127..0)
    MAX-ACCESS read-write
    STATUS current
    DESCRIPTION
    " 802.11A foreign noise threshold between -127 and 0 dBm."
   ::= {bsnRrmDot11aAPDefault 2 }

bsnRrmDot11aRFUtilizationThreshold OBJECT-TYPE
    SYNTAX INTEGER(0..100)
    MAX-ACCESS read-write
    STATUS current
    DESCRIPTION
    "802.11A RF utlization threshold between 0 and 100 percent."
   ::= {bsnRrmDot11aAPDefault 3 }

bsnRrmDot11aThroughputThreshold OBJECT-TYPE
    SYNTAX Unsigned32(1000..1000000)
    MAX-ACCESS read-write
    STATUS current
    DESCRIPTION
    " 802.11A throughput threshold between 1000 and 100000"
   ::= {bsnRrmDot11aAPDefault 4 }

bsnRrmDot11aMobilesThreshold OBJECT-TYPE
    SYNTAX INTEGER(1..75)
    MAX-ACCESS read-write
    STATUS current
    DESCRIPTION
    "802.11A mobiles threshold between 1 and 75"
   ::= {bsnRrmDot11aAPDefault 5 }

bsnRrmDot11aCoverageThreshold OBJECT-TYPE
    SYNTAX INTEGER(3..50)
    MAX-ACCESS read-write
    STATUS current
    DESCRIPTION
    " 802.11A coverage threshold between 3 and 50."
   ::= {bsnRrmDot11aAPDefault 6 }

bsnRrmDot11aMobileMinExceptionLevel OBJECT-TYPE
    SYNTAX INTEGER(1..75)
    MAX-ACCESS read-write
    STATUS current
    DESCRIPTION
    " 802.11A mobile minimum exception level between 1 and 75"
   ::= {bsnRrmDot11aAPDefault 7 }

bsnRrmDot11aCoverageExceptionLevel OBJECT-TYPE
    SYNTAX INTEGER(0..100)
    MAX-ACCESS read-write
    STATUS current
    DESCRIPTION
    " 802.11A coverage exception level between 0 and 100 percent."
   ::= {bsnRrmDot11aAPDefault 8 }


bsnRrmDot11aSignalMeasurementInterval OBJECT-TYPE
    SYNTAX  Unsigned32(60..3600)
    MAX-ACCESS read-write
    STATUS current
    DESCRIPTION
       "This interval (in secs) specifies how often do we get new 
        signal strength measurements at each Airespace AP. Default is 
        300 secs"
   DEFVAL { 300 }
   ::= {bsnRrmDot11aAPDefault 9}

bsnRrmDot11aNoiseMeasurementInterval OBJECT-TYPE
    SYNTAX  Unsigned32(60..3600)
    MAX-ACCESS read-write
    STATUS current
    DESCRIPTION
       "This interval( in secs) specifies how often do we get new 
        noise and interference measurements at each Airespace AP. 
        Default is 300 secs"
   DEFVAL { 300 }
   ::= {bsnRrmDot11aAPDefault 10}

bsnRrmDot11aLoadMeasurementInterval OBJECT-TYPE
    SYNTAX  Unsigned32(60..3600)
    MAX-ACCESS read-write
    STATUS current
    DESCRIPTION
       "This interval( in secs) specifies how often do we get new
       load measurements at each Airespace AP. Default is 300 secs"
   DEFVAL { 300 }
   ::= {bsnRrmDot11aAPDefault 11}

bsnRrmDot11aCoverageMeasurementInterval OBJECT-TYPE
    SYNTAX  Unsigned32(60..3600)
    MAX-ACCESS read-write
    STATUS current
    DESCRIPTION
       "This interval( in secs) specifies how often do we get new
       coverage measurements at each Airespace AP. Default is 300 secs"
   DEFVAL { 300 }
   ::= {bsnRrmDot11aAPDefault 12}

bsnRrmDot11aChannelMonitorList OBJECT-TYPE
    SYNTAX INTEGER {all(1),country(2),dca(3)}
    MAX-ACCESS read-write
    STATUS current
    DESCRIPTION
    "This attribute specifies the channels on which the switch monitors
     noise, interference and rogues.  The first option allows 
     monitoring on all channels while the second one on only those 
     that are supported by the country of operation. the option dca 
     implies that the monitor channel list will include those channels
     that are used by automatic channel assignment."
    ::= { bsnRrmDot11aAPDefault 13 }

--*********************************************************************
--*  Set Factory Defaults
--*********************************************************************

bsnRrmDot11aSetFactoryDefault OBJECT-TYPE
    SYNTAX  INTEGER {default(0),activate (1)}
    MAX-ACCESS read-write
    STATUS current
    DESCRIPTION
    "When set to activate all rrm parameters are reset to factory 
     defaults"
   ::= {bsnRrmDot11a 7}


-- *******************************************************************
-- * Begin of RRM dot11b Group Parameters
-- *******************************************************************
bsnRrmDot11bGroup OBJECT IDENTIFIER ::= { bsnRrmDot11b 1 }

bsnRrmDot11bGlobalAutomaticGrouping OBJECT-TYPE
    SYNTAX INTEGER {  automatic (1), off (2) }
    MAX-ACCESS read-write
    STATUS current
    DESCRIPTION
        "Dynamic grouping has two modes: on and off. When the grouping
         is off, no dynamic grouping occurs. Each Airespace Switch 
         optimizes only its own Airespace APs' parameters. When 
         grouping is on, the Airespace Switchs form groups and
         elect leaders to perform better dynamic parameter 
         optimization."
   DEFVAL { automatic }
   ::= {bsnRrmDot11bGroup 1}

bsnRrmDot11bGroupLeaderMacAddr OBJECT-TYPE
    SYNTAX MacAddress
    MAX-ACCESS read-only
    STATUS current
    DESCRIPTION
        "This is the MAC address of the group leader for the dot11b 
         group containing this Airespace Switch."
    ::= { bsnRrmDot11bGroup 2 }

bsnRrmIsDot11bGroupLeader OBJECT-TYPE
    SYNTAX INTEGER {no(0),yes(1)}
    MAX-ACCESS read-only
    STATUS current
    DESCRIPTION
        "If this Airespace Switch is a Dot11b Group Leader then this 
         attribute will be true else it will be false."
    ::= { bsnRrmDot11bGroup 3 }


bsnRrmDot11bGroupLastUpdateTime OBJECT-TYPE
    SYNTAX Unsigned32
    MAX-ACCESS read-only
    STATUS current
    DESCRIPTION
        "Last time the dot11b grouping was updated on this Airespace 
         Switch. This is valid only if the Airespace Switch is a group
         leader."
    ::= { bsnRrmDot11bGroup 4 }

bsnRrmDot11bGlobalGroupInterval OBJECT-TYPE
    SYNTAX Unsigned32
    MAX-ACCESS read-only
    STATUS current
    DESCRIPTION
        "When grouping is on, this interval(in secs) represents the 
         period with which the grouping algorithm is run. Grouping 
         algorithm will also run when the group contents changes and 
         the automatic grouping is enabled. A dynamic grouping can be 
         started upon request from the system administrator. Default 
         value is 3600 secs."
   DEFVAL { 3600 }
   ::= {bsnRrmDot11bGroup 5}


-- ************************************************************
-- * Begin of bsnWrasDot11bGroup Table
-- ************************************************************
bsnWrasDot11bGroupTable OBJECT-TYPE
    SYNTAX SEQUENCE OF BsnWrasDot11bGroupEntry
    MAX-ACCESS not-accessible
    STATUS current
    DESCRIPTION
       "This is a table of Airespace Switch addresses that identifies 
        the members of the Dot11b RF group containing this Airespace 
        Switch. Max size is 20 entries."
::= { bsnRrmDot11bGroup 9 }

bsnWrasDot11bGroupEntry OBJECT-TYPE
    SYNTAX BsnWrasDot11bGroupEntry
    MAX-ACCESS not-accessible
    STATUS current
    DESCRIPTION
        " ... "
    INDEX { bsnWrasDot11bPeerMacAddress }
    ::= { bsnWrasDot11bGroupTable 1 }

BsnWrasDot11bGroupEntry ::=
    SEQUENCE {
        bsnWrasDot11bPeerMacAddress          MacAddress,
        bsnWrasDot11bPeerIpAddress           IpAddress
    }

bsnWrasDot11bPeerMacAddress OBJECT-TYPE
    SYNTAX MacAddress
    MAX-ACCESS read-only
    STATUS current
    DESCRIPTION
        "The MAC address of the GIGE interface."
    ::= { bsnWrasDot11bGroupEntry 1 }

bsnWrasDot11bPeerIpAddress OBJECT-TYPE
    SYNTAX IpAddress
    MAX-ACCESS read-only
    STATUS current
    DESCRIPTION
        "The IP address of the Airespace Switch."
    ::= { bsnWrasDot11bGroupEntry 21 }

-- ************************************************************
-- * End of bsnWrasDot11bGroup Table
-- ************************************************************


-- ********************************************************************
-- * Begin bsnRrmDot11bAPDefault
-- *******************************************************************
bsnRrmDot11bAPDefault OBJECT IDENTIFIER ::= { bsnRrmDot11b 6 }

bsnRrmDot11bForeignInterferenceThreshold OBJECT-TYPE
    SYNTAX INTEGER(0..100)
    MAX-ACCESS read-write
    STATUS current
    DESCRIPTION
      "Foreign 802.11A interference threshold between 0 and 100 
       percent."
   ::= {bsnRrmDot11bAPDefault 1 }

bsnRrmDot11bForeignNoiseThreshold OBJECT-TYPE
    SYNTAX INTEGER(-127..0)
    MAX-ACCESS read-write
    STATUS current
    DESCRIPTION
    " 802.11A foreign noise threshold between -127 and 0 dBm."
   ::= {bsnRrmDot11bAPDefault 2 }

bsnRrmDot11bRFUtilizationThreshold OBJECT-TYPE
    SYNTAX INTEGER(0..100)
    MAX-ACCESS read-write
    STATUS current
    DESCRIPTION
    "802.11A RF utlization threshold between 0 and 100 percent."
   ::= {bsnRrmDot11bAPDefault 3 }

bsnRrmDot11bThroughputThreshold OBJECT-TYPE
    SYNTAX Unsigned32(1000..1000000)
    MAX-ACCESS read-write
    STATUS current
    DESCRIPTION
    " 802.11A Airespace AP data-rate threshold between 1000 and 100000"
   ::= {bsnRrmDot11bAPDefault 4 }

bsnRrmDot11bMobilesThreshold OBJECT-TYPE
    SYNTAX INTEGER(1..75)
    MAX-ACCESS read-write
    STATUS current
    DESCRIPTION
    "802.11A Airespace AP mobiles threshold between 1 and 75"
   ::= {bsnRrmDot11bAPDefault 5 }

bsnRrmDot11bCoverageThreshold OBJECT-TYPE
    SYNTAX INTEGER(3..50)
    MAX-ACCESS read-write
    STATUS current
    DESCRIPTION
    " 802.11A Airespace AP coverage threshold between 3 and 50."
   ::= {bsnRrmDot11bAPDefault 6 }

bsnRrmDot11bMobileMinExceptionLevel OBJECT-TYPE
    SYNTAX INTEGER(1..75)
    MAX-ACCESS read-write
    STATUS current
    DESCRIPTION
    "802.11A Airespace AP mobile minimum exception level between 1 and 
     75"
   ::= {bsnRrmDot11bAPDefault 7 }

bsnRrmDot11bCoverageExceptionLevel OBJECT-TYPE
    SYNTAX INTEGER(0..100)
    MAX-ACCESS read-write
    STATUS current
    DESCRIPTION
    "802.11A Airespace AP coverage exception level between 0 and 100 
     percent."
   ::= {bsnRrmDot11bAPDefault 8 }

bsnRrmDot11bSignalMeasurementInterval OBJECT-TYPE
    SYNTAX  Unsigned32(60..3600)
    MAX-ACCESS read-write
    STATUS current
    DESCRIPTION
      "This interval( in secs) specifies how often do we get new signal
       strength measurements at each Airespace AP. Default is 300 secs"
   DEFVAL { 300 }
   ::= {bsnRrmDot11bAPDefault 9}

bsnRrmDot11bNoiseMeasurementInterval OBJECT-TYPE
    SYNTAX  Unsigned32(60..3600)
    MAX-ACCESS read-write
    STATUS current
    DESCRIPTION
       "This interval( in secs) specifies how often do we get new 
        noise and interference measurements at each Airespace AP. 
        Default is 300 secs"
   DEFVAL { 300 }
   ::= {bsnRrmDot11bAPDefault 10}

bsnRrmDot11bLoadMeasurementInterval OBJECT-TYPE
    SYNTAX  Unsigned32(60..3600)
    MAX-ACCESS read-write
    STATUS current
    DESCRIPTION
       "This interval( in secs) specifies how often do we get new
       load measurements at each Airespace AP. Default is 300 secs"
   DEFVAL { 300 }
   ::= {bsnRrmDot11bAPDefault 11}

bsnRrmDot11bCoverageMeasurementInterval OBJECT-TYPE
    SYNTAX  Unsigned32(10..3600)
    MAX-ACCESS read-write
    STATUS current
    DESCRIPTION
       "This interval( in secs) specifies how often do we get new
       coverage measurements at each Airespace AP. Default is 300 secs"
   DEFVAL { 300 }
   ::= {bsnRrmDot11bAPDefault 12}

bsnRrmDot11bChannelMonitorList OBJECT-TYPE
    SYNTAX INTEGER {all(1),country(2),dca(3)}
    MAX-ACCESS read-write
    STATUS current
    DESCRIPTION
    "This attribute specifies the channels on which the switch 
     monitors noise, interference and rogues.
     The first option allows monitoring on all channels while the 
     second one on only those that are supported
     by the country of operation. the option dca implies that the 
     monitor channel list will include those channels
     that are used by automatic channel assignment."
    ::= { bsnRrmDot11bAPDefault 13 }

--*********************************************************************
--*  Set Factory Defaults
--*********************************************************************

bsnRrmDot11bSetFactoryDefault OBJECT-TYPE
    SYNTAX  INTEGER {default(0),activate (1)}
    MAX-ACCESS read-write
    STATUS current
    DESCRIPTION
    "When set to activate all rrm parameters are reset to factory 
     defaults"
   ::= {bsnRrmDot11b 7}

-- *******************************************************************
-- * Begin of bsnRadiusAuthServerTable
-- *******************************************************************
bsnRadiusAuthServerTable OBJECT-TYPE
      SYNTAX     SEQUENCE OF BsnRadiusAuthServerEntry
      MAX-ACCESS not-accessible
      STATUS     current
      DESCRIPTION
            "The (conceptual) table listing the RADIUS authentication
             servers with which the client shares a secret."
      ::= { bsnAAA 1 }


bsnRadiusAuthServerEntry OBJECT-TYPE
      SYNTAX     BsnRadiusAuthServerEntry
      MAX-ACCESS not-accessible
      STATUS     current
      DESCRIPTION
            "An entry (conceptual row) representing a RADIUS
             authentication server with which the client shares
             a secret."
      INDEX      { bsnRadiusAuthServerIndex }
      ::= { bsnRadiusAuthServerTable 1 }

BsnRadiusAuthServerEntry ::= SEQUENCE {
      bsnRadiusAuthServerIndex                    Integer32,
      bsnRadiusAuthServerAddress                  IpAddress,
      bsnRadiusAuthClientServerPortNumber         Integer32,
      bsnRadiusAuthServerKey                      OCTET STRING,
      bsnRadiusAuthServerStatus                   INTEGER,
      bsnRadiusAuthServerKeyFormat                INTEGER,
      bsnRadiusAuthServerRFC3576                  INTEGER,
      bsnRadiusAuthServerIPSec                    INTEGER,
      bsnRadiusAuthServerIPSecAuth                INTEGER,
      bsnRadiusAuthServerIPSecEncryption          INTEGER,
      bsnRadiusAuthServerIPSecIKEPhase1           INTEGER,
      bsnRadiusAuthServerIPSecIKELifetime         Integer32,
      bsnRadiusAuthServerIPSecDHGroup             INTEGER,
      bsnRadiusAuthServerNetworkUserConfig        INTEGER,
      bsnRadiusAuthServerMgmtUserConfig           INTEGER,
      bsnRadiusAuthServerRetransmitTimeout        INTEGER,
      bsnRadiusAuthServerKeyWrapKEKkey            OCTET STRING,
      bsnRadiusAuthServerKeyWrapMACKkey           OCTET STRING,
      bsnRadiusAuthServerKeyWrapFormat            INTEGER,
      bsnRadiusAuthServerRowStatus                RowStatus
}

bsnRadiusAuthServerIndex OBJECT-TYPE
      SYNTAX     Integer32 (1..17)
      MAX-ACCESS read-create
      STATUS     current
      DESCRIPTION
             "A number uniquely identifying each RADIUS
             Authentication server with which this client
             communicates."
      ::= { bsnRadiusAuthServerEntry 1 }

bsnRadiusAuthServerAddress OBJECT-TYPE
      SYNTAX     IpAddress
      MAX-ACCESS read-create
      STATUS     current
      DESCRIPTION
            "The IP address of the RADIUS authentication server
             referred to in this table entry."
      ::= { bsnRadiusAuthServerEntry 2 }

bsnRadiusAuthClientServerPortNumber  OBJECT-TYPE
      SYNTAX Integer32 (0..65535)
      MAX-ACCESS read-create
      STATUS current
      DESCRIPTION
            "The UDP port the client is using to send requests to
             this server."
      ::= { bsnRadiusAuthServerEntry 3 }

bsnRadiusAuthServerKey OBJECT-TYPE
        SYNTAX  OCTET STRING (SIZE(0..128))
        MAX-ACCESS  read-create
        STATUS  current
        DESCRIPTION
                "The authentication and encryption key shared between
                the Radius client and this Radius Server.
                When the bsnRadiusAuthServerKeyFormat is hex it
                can have max length of 128 bytes. If the 
                bsnRadiusAuthServerKeyFormat is Ascii it can have
                max length of 64 bytes.
                "
        DEFVAL { "" }
        ::= { bsnRadiusAuthServerEntry 4 }

bsnRadiusAuthServerStatus  OBJECT-TYPE
      SYNTAX INTEGER { disable(0),enable (1)}
      MAX-ACCESS read-create
      STATUS current
      DESCRIPTION
            "Server enable or disable status."
      ::= { bsnRadiusAuthServerEntry 5 }

bsnRadiusAuthServerKeyFormat  OBJECT-TYPE
      SYNTAX INTEGER { hex(1),ascii (2)}
      MAX-ACCESS read-create
      STATUS current
      DESCRIPTION
            "Format of the server key. When hex, the number of 
             characters in the key should be even."
      ::= { bsnRadiusAuthServerEntry 6 }

bsnRadiusAuthServerRFC3576   OBJECT-TYPE
        SYNTAX INTEGER { disable (0), enable (1)}
        MAX-ACCESS read-create
        STATUS current
        DESCRIPTION
            "Support for Dynamic Authorization Extensions to RADIUS."
        DEFVAL { enable }
        ::= { bsnRadiusAuthServerEntry 7 }

bsnRadiusAuthServerIPSec     OBJECT-TYPE
        SYNTAX INTEGER { disable (0), enable (1)}
        MAX-ACCESS read-create
        STATUS current
        DESCRIPTION
            "IPSec over RADIUS"
        DEFVAL { disable }
        ::= { bsnRadiusAuthServerEntry 8 }

bsnRadiusAuthServerIPSecAuth      OBJECT-TYPE
        SYNTAX INTEGER { none (0), hmacMd5 (1) , hmacSha1 (2) }
                MAX-ACCESS read-create
        STATUS current
        DESCRIPTION
                "The Hash algorithm employed by the IPSec Encrpytion.
                 This applies only when bsnRadiusAuthServerIPSec is in
                 enable state."
        DEFVAL { hmacSha1 }
    ::= { bsnRadiusAuthServerEntry 9 }

bsnRadiusAuthServerIPSecEncryption  OBJECT-TYPE
        SYNTAX INTEGER { none (0),
                         des (1),
                         tripleDes (2),
                         aesCbc (3)
                       }
        MAX-ACCESS read-create
        STATUS current
        DESCRIPTION
                "The Encryption algorithm employed by this IpSec 
                 Encryption.  This applies only when 
                 bsnRadiusAuthServerIPSec is in enable state."
        DEFVAL { tripleDes }
    ::= { bsnRadiusAuthServerEntry 10 }

 bsnRadiusAuthServerIPSecIKEPhase1          OBJECT-TYPE
        SYNTAX INTEGER { main (1),agressive (2) }
                MAX-ACCESS read-create
        STATUS current
        DESCRIPTION
                "VPN IKE Phase 1 Mode type as per the IpSec standards.
                This applies only when bsnRadiusAuthServerIPSec is in 
                enable state."
        DEFVAL {main}
    ::= { bsnRadiusAuthServerEntry 11 }


bsnRadiusAuthServerIPSecIKELifetime        OBJECT-TYPE
        SYNTAX Integer32 (1800..345600)
                MAX-ACCESS read-create
        STATUS current
        DESCRIPTION
               "IPSec IKE's Lifetime.
                This applies only when bsnRadiusAuthServerIPSec is in 
                enable state."
        DEFVAL {28800}
    ::= { bsnRadiusAuthServerEntry 12 }


bsnRadiusAuthServerIPSecDHGroup         OBJECT-TYPE
        SYNTAX INTEGER { group1 (1),group2 (2),group5 (5)}
                MAX-ACCESS read-create
        STATUS current
        DESCRIPTION
                "IKE's Diffie-Hellman Group.
                This applies only when bsnRadiusAuthServerIPSec is in 
                enable state."
        DEFVAL {group2}
    ::= { bsnRadiusAuthServerEntry 13 }

bsnRadiusAuthServerNetworkUserConfig  OBJECT-TYPE
      SYNTAX INTEGER { disable(0),enable (1)}
      MAX-ACCESS read-create
      STATUS current
      DESCRIPTION
            "When enabled, this entry is considered as network user 
             radius authenticating server entry."
      ::= { bsnRadiusAuthServerEntry 14 }

bsnRadiusAuthServerMgmtUserConfig  OBJECT-TYPE
      SYNTAX INTEGER { disable(0),enable (1)}
      MAX-ACCESS read-create
      STATUS current
      DESCRIPTION
            "When enabled, this entry is considered as management user
             radius authenticating server entry."
      ::= { bsnRadiusAuthServerEntry 15 }

bsnRadiusAuthServerRetransmitTimeout OBJECT-TYPE
    SYNTAX INTEGER(2..30)
    MAX-ACCESS read-create
    STATUS current
    DESCRIPTION
            "Time in seconds after which a radius authentication 
             request will timeout and a retransmission will be taken 
             up by the switch."
      ::= {bsnRadiusAuthServerEntry 17 }

bsnRadiusAuthServerKeyWrapKEKkey  OBJECT-TYPE 
      SYNTAX            OCTET STRING
      MAX-ACCESS        read-create
      STATUS            current
      DESCRIPTION
        "Key-encryption-key (KEK) used as the key for the 128 bit
         AES Key Wrap algorithm to encrypt the PMK in the key 
         attribute. If the key is present in request, it should be 
         taken as a hint by the server that the sender prefers this 
         method of encryption over others. 
         To maintain security actual keys after configuration are never
         returned in get request. If keys are configured then '***' 
         is returned. If keys are not configured then empty string is 
         retunred. 
         bsnRadiusAuthServerKeyFormat is used this key. 
         if the format chosen is ascii then it should be 16 bytes in 
         length.  if the format chosen is hex then it should be 32 
         bytes in length."
      ::= {bsnRadiusAuthServerEntry 18 }
      
bsnRadiusAuthServerKeyWrapMACKkey  OBJECT-TYPE 
      SYNTAX            OCTET STRING
      MAX-ACCESS        read-create
      STATUS            current
      DESCRIPTION
       "Message-authenticator-code-key ( MACK) - used as the key for 
       the HMAC-SHA-1 algorithm to sign the RADIUS message to prevent 
       spoofing. MACK must be configured when KEK is configured. 
       To maintain security actual keys after configuration are never
       returned in get request. If keys are configured then '***' 
       is returned. If keys are not configured then empty string is 
       returned. 
       bsnRadiusAuthServerKeyFormat is used this key. 
       if the format chosen is ascii then it should be 20 bytes in 
       length. If the format chosen is hex then it should be 40 bytes 
       in length. 
       "
      ::= {bsnRadiusAuthServerEntry 19 }

bsnRadiusAuthServerKeyWrapFormat  OBJECT-TYPE
      SYNTAX INTEGER { hex(1),ascii (2)}
      MAX-ACCESS read-create
      STATUS current
      DESCRIPTION
            "Format for the Key Wrap keys. This object is mandatory  
             for manager to send if the key Wrap keys are being 
             configured. Get on this object will always return hex(1)"
      ::= { bsnRadiusAuthServerEntry 20 }

bsnRadiusAuthServerRowStatus  OBJECT-TYPE
      SYNTAX RowStatus
      MAX-ACCESS read-create
      STATUS current
      DESCRIPTION
    " Row Status for creation/deletion"
      ::= { bsnRadiusAuthServerEntry 26 }


-- *******************************************************************
-- * Begin of bsnRadiusAccServerTable
-- *******************************************************************

bsnRadiusAccServerTable OBJECT-TYPE
      SYNTAX SEQUENCE OF BsnRadiusAccServerEntry
      MAX-ACCESS not-accessible
      STATUS     current
      DESCRIPTION
            "The (conceptual) table listing the RADIUS accounting
             servers with which the client shares a secret."
      ::= { bsnAAA 2 }

bsnRadiusAccServerEntry OBJECT-TYPE
      SYNTAX     BsnRadiusAccServerEntry
      MAX-ACCESS not-accessible
      STATUS     current
      DESCRIPTION
            "An entry (conceptual row) representing a RADIUS
             accounting server with which the client shares a secret."
      INDEX      { bsnRadiusAccServerIndex }
      ::= { bsnRadiusAccServerTable 1 }

BsnRadiusAccServerEntry ::= SEQUENCE {
      bsnRadiusAccServerIndex                  Integer32,
      bsnRadiusAccServerAddress                IpAddress,
      bsnRadiusAccClientServerPortNumber       Integer32,
      bsnRadiusAccServerKey                    OCTET STRING,
      bsnRadiusAccServerStatus                 INTEGER,
      bsnRadiusAccServerKeyFormat              INTEGER,
      bsnRadiusAccServerIPSec                  INTEGER,
      bsnRadiusAccServerIPSecAuth              INTEGER,
      bsnRadiusAccServerIPSecEncryption        INTEGER,
      bsnRadiusAccServerIPSecIKEPhase1         INTEGER,
      bsnRadiusAccServerIPSecIKELifetime       Integer32,
      bsnRadiusAccServerIPSecDHGroup           INTEGER,
      bsnRadiusAccServerNetworkUserConfig      INTEGER,
      bsnRadiusAccServerRetransmitTimeout      INTEGER,
      bsnRadiusAccServerRowStatus              RowStatus
}

bsnRadiusAccServerIndex OBJECT-TYPE
      SYNTAX     Integer32 (1..17)
      MAX-ACCESS read-create
      STATUS     current
      DESCRIPTION
            "A number uniquely identifying each RADIUS
             Accounting server with which this client
             communicates."
      ::= { bsnRadiusAccServerEntry 1 }

bsnRadiusAccServerAddress OBJECT-TYPE
      SYNTAX     IpAddress
      MAX-ACCESS read-create
      STATUS     current
      DESCRIPTION
            "The IP address of the RADIUS accounting server
             referred to in this table entry."
      ::= { bsnRadiusAccServerEntry 2 }

bsnRadiusAccClientServerPortNumber  OBJECT-TYPE
      SYNTAX Integer32 (0..65535)
      MAX-ACCESS read-create
      STATUS current
      DESCRIPTION
            "The UDP port the client is using to send requests to
             this server."
      ::= { bsnRadiusAccServerEntry 3 }

bsnRadiusAccServerKey OBJECT-TYPE
        SYNTAX  OCTET STRING (SIZE(0..128))
        MAX-ACCESS  read-create
        STATUS  current
        DESCRIPTION
                "The authentication and encryption key shared between
                the Radius client and this Radius Server.
                When the bsnRadiusAccServerKeyFormat is hex it
                can have max length of 128 bytes. If the 
                bsnRadiusAccServerKeyFormat  is Ascii it can have
                max length of 64 bytes."
        DEFVAL { "" }
        ::= { bsnRadiusAccServerEntry 4 }

bsnRadiusAccServerStatus  OBJECT-TYPE
      SYNTAX INTEGER { disable(0),enable (1)}
      MAX-ACCESS read-create
      STATUS current
      DESCRIPTION
            "Server enable or disable status."
      ::= { bsnRadiusAccServerEntry 5 }

bsnRadiusAccServerKeyFormat  OBJECT-TYPE
      SYNTAX INTEGER { hex(1),ascii (2)}
      MAX-ACCESS read-create
      STATUS current
      DESCRIPTION
            "Format of the server key. When hex, the number of 
             characters in the key should be even."
      ::= { bsnRadiusAccServerEntry 6 }

bsnRadiusAccServerIPSec     OBJECT-TYPE
        SYNTAX INTEGER { disable (0), enable (1)}
        MAX-ACCESS read-create
        STATUS current
        DESCRIPTION
            "IPSec over RADIUS"
        DEFVAL { disable }
        ::= { bsnRadiusAccServerEntry 7 }

bsnRadiusAccServerIPSecAuth      OBJECT-TYPE
        SYNTAX INTEGER { none (0), hmacMd5 (1) , hmacSha1 (2) }
                MAX-ACCESS read-create
        STATUS current
        DESCRIPTION
                "The Hash algorithm employed by the IPSec Encrpytion.
                 This applies only when bsnRadiusAccServerIPSec is in 
                 enable state."
        DEFVAL { hmacSha1 }
    ::= { bsnRadiusAccServerEntry 8 }

bsnRadiusAccServerIPSecEncryption  OBJECT-TYPE
        SYNTAX INTEGER { none (0),
                         des (1),
                         tripleDes (2),
                         aesCbc (3)
                       }
        MAX-ACCESS read-create
        STATUS current
        DESCRIPTION
                "The Encryption algorithm employed by this IpSec 
                 Encryption. This applies only when 
                 bsnRadiusAccServerIPSec is in enable state."
        DEFVAL { tripleDes }
    ::= { bsnRadiusAccServerEntry 9 }

bsnRadiusAccServerIPSecIKEPhase1          OBJECT-TYPE
        SYNTAX INTEGER { main (1),agressive (2) }
                MAX-ACCESS read-create
        STATUS current
        DESCRIPTION
               "VPN IKE Phase 1 Mode type as per the IpSec standards.
                This applies only when bsnRadiusAccServerIPSec is in 
                enable state."
        DEFVAL {main}
    ::= { bsnRadiusAccServerEntry 10 }


bsnRadiusAccServerIPSecIKELifetime        OBJECT-TYPE
        SYNTAX Integer32 (1800..345600)
                MAX-ACCESS read-create
        STATUS current
        DESCRIPTION
                "IPSec IKE's Lifetime.
                This applies only when bsnRadiusAccServerIPSec is in 
                enable state."
        DEFVAL {28800}
    ::= { bsnRadiusAccServerEntry 11 }

bsnRadiusAccServerIPSecDHGroup         OBJECT-TYPE
        SYNTAX INTEGER { group1 (1),group2 (2),group5 (5)}
                MAX-ACCESS read-create
        STATUS current
        DESCRIPTION
                "IKE's Diffie-Hellman Group.
                This applies only when bsnRadiusAccServerIPSec is in 
                enable state."
        DEFVAL {group2}
    ::= { bsnRadiusAccServerEntry 12 }

bsnRadiusAccServerNetworkUserConfig  OBJECT-TYPE
      SYNTAX INTEGER { disable(0),enable (1)}
      MAX-ACCESS read-create
      STATUS current
      DESCRIPTION
            "When enabled, this entry is considered as network user 
             radius accounting server entry."
      ::= { bsnRadiusAccServerEntry 13 }

bsnRadiusAccServerRetransmitTimeout OBJECT-TYPE
    SYNTAX INTEGER(2..30)
    MAX-ACCESS read-create
    STATUS current
    DESCRIPTION
            "Time in seconds after which a radius accounting request 
             will timeout and a retransmission will be taken up by 
             the switch."
      ::= {bsnRadiusAccServerEntry 14 }

bsnRadiusAccServerRowStatus  OBJECT-TYPE
      SYNTAX RowStatus
      MAX-ACCESS read-create
      STATUS current
      DESCRIPTION
    " Row Status for creation/deletion"
      ::= { bsnRadiusAccServerEntry 26 }


-- *******************************************************************
-- * Begin of bsnRadiusAuthServerStatsTable
-- *******************************************************************
bsnRadiusAuthServerStatsTable OBJECT-TYPE
      SYNTAX     SEQUENCE OF BsnRadiusAuthServerStatsEntry
      MAX-ACCESS not-accessible
      STATUS     current
      DESCRIPTION
            "The listing the Statistics of RADIUS authentication
             servers."
      ::= { bsnAAA 3 }


bsnRadiusAuthServerStatsEntry OBJECT-TYPE
      SYNTAX     BsnRadiusAuthServerStatsEntry
      MAX-ACCESS not-accessible
      STATUS     current
      DESCRIPTION
            "An entry representing statistics a RADIUS
             authentication server with which the client shares
             a secret."
      INDEX      { bsnRadiusAuthServerIndex }
      ::= { bsnRadiusAuthServerStatsTable 1 }

BsnRadiusAuthServerStatsEntry ::= SEQUENCE {
      bsnRadiusAuthClientRoundTripTime                   TimeTicks,
      bsnRadiusAuthClientAccessRequests                  Counter32,
      bsnRadiusAuthClientAccessRetransmissions           Counter32,
      bsnRadiusAuthClientAccessAccepts                   Counter32,
      bsnRadiusAuthClientAccessRejects                   Counter32,
      bsnRadiusAuthClientAccessChallenges                Counter32,
      bsnRadiusAuthClientMalformedAccessResponses        Counter32,
      bsnRadiusAuthClientBadAuthenticators               Counter32,
      bsnRadiusAuthClientPendingRequests                  Gauge32,
      bsnRadiusAuthClientTimeouts                        Counter32,
      bsnRadiusAuthClientUnknownTypes                    Counter32,
      bsnRadiusAuthClientPacketsDropped                  Counter32
}

bsnRadiusAuthClientRoundTripTime  OBJECT-TYPE
      SYNTAX TimeTicks
      MAX-ACCESS read-only
      STATUS current
      DESCRIPTION
            "The time interval (in hundredths of a second) between
             the most recent Access-Reply/Access-Challenge and the
             Access-Request that matched it from this RADIUS
             authentication server."
      ::= { bsnRadiusAuthServerStatsEntry 6 }

-- *************************************************************
-- Request/Response statistics
--
-- TotalIncomingPackets = Accepts + Rejects + Challenges + UnknownTypes
--
-- TotalIncomingPackets - MalformedResponses - BadAuthenticators -
-- UnknownTypes - PacketsDropped = Successfully received
--
-- AccessRequests + PendingRequests + ClientTimeouts =
-- Successfully Received
-- *************************************************************

bsnRadiusAuthClientAccessRequests OBJECT-TYPE
      SYNTAX Counter32
      MAX-ACCESS read-only
      STATUS current
      DESCRIPTION
            "The number of RADIUS Access-Request packets sent
             to this server. This does not include retransmissions."
      ::= { bsnRadiusAuthServerStatsEntry 7 }

bsnRadiusAuthClientAccessRetransmissions OBJECT-TYPE
      SYNTAX Counter32
      MAX-ACCESS read-only
      STATUS current
      DESCRIPTION
            "The number of RADIUS Access-Request packets
             retransmitted to this RADIUS authentication server."
      ::= { bsnRadiusAuthServerStatsEntry 8 }

bsnRadiusAuthClientAccessAccepts OBJECT-TYPE
      SYNTAX Counter32
      MAX-ACCESS read-only
      STATUS current
      DESCRIPTION
            "The number of RADIUS Access-Accept packets
             (valid or invalid) received from this server."
      ::= { bsnRadiusAuthServerStatsEntry 9 }

bsnRadiusAuthClientAccessRejects OBJECT-TYPE
      SYNTAX Counter32
      MAX-ACCESS read-only
      STATUS current
      DESCRIPTION
            "The number of RADIUS Access-Reject packets
             (valid or invalid) received from this server."
      ::= { bsnRadiusAuthServerStatsEntry  10 }

bsnRadiusAuthClientAccessChallenges OBJECT-TYPE
      SYNTAX Counter32
      MAX-ACCESS read-only
      STATUS current
      DESCRIPTION
            "The number of RADIUS Access-Challenge packets
             (valid or invalid) received from this server."
      ::= { bsnRadiusAuthServerStatsEntry 11 }

-- "Access-Response" includes an Access-Accept, Access-Challenge
-- or Access-Reject

bsnRadiusAuthClientMalformedAccessResponses OBJECT-TYPE
      SYNTAX Counter32
      MAX-ACCESS read-only
      STATUS current
      DESCRIPTION
            "The number of malformed RADIUS Access-Response
             packets received from this server.
             Malformed packets include packets with
             an invalid length. Bad authenticators or
             Signature attributes or unknown types are not
             included as malformed access responses."
      ::= { bsnRadiusAuthServerStatsEntry 12 }

bsnRadiusAuthClientBadAuthenticators OBJECT-TYPE
      SYNTAX Counter32
      MAX-ACCESS read-only
      STATUS current
      DESCRIPTION
            "The number of RADIUS Access-Response packets
             containing invalid authenticators or Signature
             attributes received from this server."
      ::= { bsnRadiusAuthServerStatsEntry 13 }

bsnRadiusAuthClientPendingRequests OBJECT-TYPE
      SYNTAX Gauge32
      MAX-ACCESS read-only
      STATUS current
      DESCRIPTION
            "The number of RADIUS Access-Request packets
             destined for this server that have not yet timed out
             or received a response. This variable is incremented
             when an Access-Request is sent and decremented due to
             receipt of an Acess-Accept, Access-Reject or
             Access-Challenge, a timeout or retransmission."
      ::= { bsnRadiusAuthServerStatsEntry 14 }

bsnRadiusAuthClientTimeouts OBJECT-TYPE
     SYNTAX Counter32
     MAX-ACCESS read-only
     STATUS current
     DESCRIPTION
            "The number of authentication timeouts to this server.
             After a timeout the client may retry to the same
             server, send to a different server, or
             give up. A retry to the same server is counted as a
             retransmit as well as a timeout. A send to a different
             server is counted as a Request as well as a timeout."
      ::= { bsnRadiusAuthServerStatsEntry  15 }

bsnRadiusAuthClientUnknownTypes OBJECT-TYPE
      SYNTAX Counter32
      MAX-ACCESS read-only
      STATUS current
      DESCRIPTION
            "The number of RADIUS packets of unknown type which
             were received from this server on the authentication port."
      ::= { bsnRadiusAuthServerStatsEntry  16 }


bsnRadiusAuthClientPacketsDropped OBJECT-TYPE
      SYNTAX Counter32
      MAX-ACCESS read-only
      STATUS current
      DESCRIPTION
            "The number of RADIUS packets of which were
             received from this server on the authentication port
             and dropped for some other reason."
      ::= { bsnRadiusAuthServerStatsEntry  36 }

-- *******************************************************************
-- * Begin of bsnRadiusAccServerStatsTable
-- *******************************************************************

bsnRadiusAccServerStatsTable OBJECT-TYPE
      SYNTAX SEQUENCE OF BsnRadiusAccServerStatsEntry
      MAX-ACCESS not-accessible
      STATUS     current
      DESCRIPTION
            "The (conceptual) table listing the RADIUS accounting
             servers with which the client shares a secret."
      ::= { bsnAAA 4 }

bsnRadiusAccServerStatsEntry OBJECT-TYPE
      SYNTAX     BsnRadiusAccServerStatsEntry
      MAX-ACCESS not-accessible
      STATUS     current
      DESCRIPTION
            "An entry (conceptual row) representing a RADIUS
             accounting server with which the client shares a secret."
      INDEX      { bsnRadiusAccServerIndex }
      ::= { bsnRadiusAccServerStatsTable 1 }

BsnRadiusAccServerStatsEntry ::= SEQUENCE {
      bsnRadiusAccClientRoundTripTime                   TimeTicks,
      bsnRadiusAccClientRequests                        Counter32,
      bsnRadiusAccClientRetransmissions                 Counter32,
      bsnRadiusAccClientResponses                       Counter32,
      bsnRadiusAccClientMalformedResponses              Counter32,
      bsnRadiusAccClientBadAuthenticators               Counter32,
      bsnRadiusAccClientPendingRequests                 Gauge32,
      bsnRadiusAccClientTimeouts                        Counter32,
      bsnRadiusAccClientUnknownTypes                    Counter32,
      bsnRadiusAccClientPacketsDropped                  Counter32
}

bsnRadiusAccClientRoundTripTime  OBJECT-TYPE
      SYNTAX TimeTicks
      MAX-ACCESS read-only
      STATUS current
      DESCRIPTION
             "The time interval between the most recent
             Accounting-Response and the Accounting-Request that
             matched it from this RADIUS accounting server."
      ::= { bsnRadiusAccServerStatsEntry 6 }

-- *************************************************************
-- Request/Response statistics
--
-- Requests = Responses + PendingRequests + ClientTimeouts
--
-- Responses - MalformedResponses - BadAuthenticators -
-- UnknownTypes - PacketsDropped = Successfully received
-- *************************************************************

bsnRadiusAccClientRequests OBJECT-TYPE
      SYNTAX Counter32
      MAX-ACCESS read-only
      STATUS current
      DESCRIPTION
            "The number of RADIUS Accounting-Request packets
             sent. This does not include retransmissions."
      ::= { bsnRadiusAccServerStatsEntry 7 }

bsnRadiusAccClientRetransmissions OBJECT-TYPE
      SYNTAX Counter32
      MAX-ACCESS read-only
      STATUS current
      DESCRIPTION
            "The number of RADIUS Accounting-Request packets
             retransmitted to this RADIUS accounting server.
             Retransmissions include retries where the
             Identifier and Acct-Delay have been updated, as
             well as those in which they remain the same."
      ::= { bsnRadiusAccServerStatsEntry 8 }

bsnRadiusAccClientResponses OBJECT-TYPE
      SYNTAX Counter32
      MAX-ACCESS read-only
      STATUS current
      DESCRIPTION
            "The number of RADIUS packets received on the
             accounting port from this server."
      ::= { bsnRadiusAccServerStatsEntry 9 }

bsnRadiusAccClientMalformedResponses OBJECT-TYPE
      SYNTAX Counter32
      MAX-ACCESS read-only
      STATUS current
      DESCRIPTION
             "The number of malformed RADIUS Accounting-Response
              packets received from this server. Malformed packets
             include packets with an invalid length. Bad
             authenticators and unknown types are not included as
             malformed accounting responses."
      ::= { bsnRadiusAccServerStatsEntry 10 }

bsnRadiusAccClientBadAuthenticators OBJECT-TYPE
      SYNTAX Counter32
      MAX-ACCESS read-only
      STATUS current
      DESCRIPTION
            "The number of RADIUS Accounting-Response
             packets which contained invalid authenticators
             received from this server."
      ::= { bsnRadiusAccServerStatsEntry 11 }

bsnRadiusAccClientPendingRequests OBJECT-TYPE
      SYNTAX Gauge32
      MAX-ACCESS read-only
      STATUS current
      DESCRIPTION
            "The number of RADIUS Accounting-Request packets
             sent to this server that have not yet timed out or
             received a response. This variable is incremented when an
             Accounting-Request is sent and decremented due to
             receipt of an Accounting-Response, a timeout or
             a retransmission."
      ::= { bsnRadiusAccServerStatsEntry 12 }

bsnRadiusAccClientTimeouts OBJECT-TYPE
     SYNTAX Counter32
     MAX-ACCESS read-only
     STATUS current
     DESCRIPTION
          "The number of accounting timeouts to this server.
           After a timeout the client may retry to the same
           server, send to a different server, or give up.
           A retry to the same server is counted as a
           retransmit as well as a timeout. A send to a different
           server is counted as an Accounting-Request as well as
           a timeout."
      ::= { bsnRadiusAccServerStatsEntry  13 }

bsnRadiusAccClientUnknownTypes OBJECT-TYPE
      SYNTAX Counter32
      MAX-ACCESS read-only
      STATUS current
      DESCRIPTION
            "The number of RADIUS packets of unknown type which
             were received from this server on the accounting port."
      ::= { bsnRadiusAccServerStatsEntry  14 }

bsnRadiusAccClientPacketsDropped OBJECT-TYPE
      SYNTAX Counter32
      MAX-ACCESS read-only
      STATUS current
      DESCRIPTION
            "The number of RADIUS packets which were received from
             this server on the accounting port and dropped for some
             other reason."
      ::= { bsnRadiusAccServerStatsEntry  34 }

-- *******************************************************************
-- bsnUsersTable
-- *******************************************************************

bsnUsersTable OBJECT-TYPE
      SYNTAX     SEQUENCE OF BsnUsersEntry
      MAX-ACCESS not-accessible
      STATUS     obsolete
      DESCRIPTION
            "The (conceptual) table listing Wlan Users"
      ::= { bsnAAA 5 }


bsnUsersEntry OBJECT-TYPE
      SYNTAX     BsnUsersEntry
      MAX-ACCESS not-accessible
      STATUS     obsolete
      DESCRIPTION
            "...."
      INDEX      { bsnUserName }
      ::= { bsnUsersTable 1 }

BsnUsersEntry ::= SEQUENCE {
                bsnUserName            OCTET STRING,
                bsnUserPassword        OCTET STRING,
                bsnUserEssIndex        INTEGER,
                bsnUserAccessMode      INTEGER,
                bsnUserType            INTEGER,
                bsnUserInterfaceName   OCTET STRING,
                bsnUserRowStatus       RowStatus
}

bsnUserName OBJECT-TYPE
      SYNTAX     OCTET STRING (SIZE(1..24))
      MAX-ACCESS read-create
      STATUS     obsolete
      DESCRIPTION
             "User Name"
      ::= { bsnUsersEntry 2 }

bsnUserPassword OBJECT-TYPE
      SYNTAX     OCTET STRING (SIZE(1..24))
      MAX-ACCESS read-create
      STATUS     obsolete
      DESCRIPTION
             "User Password"
      ::= { bsnUsersEntry 3 }

bsnUserEssIndex OBJECT-TYPE
      SYNTAX     INTEGER (0..17)
      MAX-ACCESS read-create
      STATUS     obsolete
      DESCRIPTION
             "User WLAN ID. Value 0 implies that this applies to any 
              WLAN ID."
      ::= { bsnUsersEntry 4 }

bsnUserAccessMode OBJECT-TYPE
      SYNTAX     INTEGER { readOnly (1) , readWrite (2)}
      MAX-ACCESS read-create
      STATUS     obsolete
      DESCRIPTION
             "User Access Mode."
      ::= { bsnUsersEntry 5 }

bsnUserType OBJECT-TYPE
      SYNTAX     INTEGER { management (1),wlan(2),macFilter(3)}
      MAX-ACCESS read-create
      STATUS     obsolete
      DESCRIPTION
             "User Type."
      ::= { bsnUsersEntry 6 }

bsnUserInterfaceName OBJECT-TYPE
      SYNTAX     OCTET STRING (SIZE(0..32))
      MAX-ACCESS read-create
      STATUS     obsolete
      DESCRIPTION
             "Interface Name."
      ::= { bsnUsersEntry 7 }

bsnUserRowStatus OBJECT-TYPE
      SYNTAX     RowStatus
      MAX-ACCESS read-create
      STATUS     obsolete
      DESCRIPTION
             "Row Status"
      ::= { bsnUsersEntry 26 }

-- *******************************************************************
-- bsnMacFilterTable
-- *******************************************************************

bsnMacFilterTable OBJECT-TYPE
      SYNTAX     SEQUENCE OF BsnMacFilterEntry
      MAX-ACCESS not-accessible
      STATUS     current
      DESCRIPTION
            "The table listing MAC Filter entries"
      ::= { bsnAAA 9 }


bsnMacFilterEntry OBJECT-TYPE
      SYNTAX     BsnMacFilterEntry
      MAX-ACCESS not-accessible
      STATUS     current
      DESCRIPTION
            "...."
      INDEX      { bsnMacFilterAddress }
      ::= { bsnMacFilterTable 1 }

BsnMacFilterEntry ::= SEQUENCE {
                bsnMacFilterAddress         OCTET STRING,
                bsnMacFilterWlanId          INTEGER,
                bsnMacFilterInterfaceName   OCTET STRING,
                bsnMacFilterDescription     OCTET STRING,
                bsnMacFilterRowStatus       RowStatus
}

bsnMacFilterAddress OBJECT-TYPE
      SYNTAX     OCTET STRING (SIZE(1..24))
      MAX-ACCESS read-create
      STATUS     current
      DESCRIPTION
             "MAC Address of the entry"
      ::= { bsnMacFilterEntry 1 }

bsnMacFilterWlanId OBJECT-TYPE
      SYNTAX     INTEGER (0..17)
      MAX-ACCESS read-create
      STATUS     current
      DESCRIPTION
             "WLAN ID of the WLAN that the user can connect to. 0 
              means any WLAN ID."
      ::= { bsnMacFilterEntry 2 }

bsnMacFilterInterfaceName OBJECT-TYPE
      SYNTAX     OCTET STRING (SIZE(0..32))
      MAX-ACCESS read-create
      STATUS     current
      DESCRIPTION
             "Interface Name."
      ::= { bsnMacFilterEntry 3 }

bsnMacFilterDescription OBJECT-TYPE
      SYNTAX     OCTET STRING (SIZE(0..32))
      MAX-ACCESS read-create
      STATUS     current
      DESCRIPTION
             "Description of the MAC Filter entry."
      ::= { bsnMacFilterEntry 4 }

bsnMacFilterRowStatus OBJECT-TYPE
      SYNTAX     RowStatus
      MAX-ACCESS read-create
      STATUS     current
      DESCRIPTION
             "Row Status"
      ::= { bsnMacFilterEntry 24 }

-- *******************************************************************
-- bsnLocalNetUserTable
-- *******************************************************************

bsnLocalNetUserTable OBJECT-TYPE
      SYNTAX     SEQUENCE OF BsnLocalNetUserEntry
      MAX-ACCESS not-accessible
      STATUS     current
      DESCRIPTION
            "The table listing Local Net User entries."
      ::= { bsnAAA 10 }


bsnLocalNetUserEntry OBJECT-TYPE
      SYNTAX     BsnLocalNetUserEntry
      MAX-ACCESS not-accessible
      STATUS     current
      DESCRIPTION
            "...."
      INDEX      { bsnLocalNetUserName }
      ::= { bsnLocalNetUserTable 1 }

BsnLocalNetUserEntry ::= SEQUENCE {
                bsnLocalNetUserName             OCTET STRING,
                bsnLocalNetUserWlanId           INTEGER,
                bsnLocalNetUserPassword         OCTET STRING,
                bsnLocalNetUserDescription      OCTET STRING,
                bsnLocalNetUserLifetime         TimeInterval,
                bsnLocalNetUserStartTime        TimeTicks,
                bsnLocalNetUserRemainingTime    TimeInterval,
                bsnLocalNetUserRowStatus        RowStatus
}

bsnLocalNetUserName OBJECT-TYPE
      SYNTAX     OCTET STRING (SIZE(1..24))
      MAX-ACCESS read-create
      STATUS     current
      DESCRIPTION
             "Name of the net user."
      ::= { bsnLocalNetUserEntry 1 }

bsnLocalNetUserWlanId OBJECT-TYPE
      SYNTAX     INTEGER (0..17)
      MAX-ACCESS read-create
      STATUS     current
      DESCRIPTION
             "WLAN ID of the WLAN that the user can connect to. 0 
              means any WLAN ID."
      ::= { bsnLocalNetUserEntry 2 }

bsnLocalNetUserPassword OBJECT-TYPE
      SYNTAX     OCTET STRING (SIZE(0..24))
      MAX-ACCESS read-create
      STATUS     current
      DESCRIPTION
             "User Password."
      ::= { bsnLocalNetUserEntry 3 }

bsnLocalNetUserDescription OBJECT-TYPE
      SYNTAX     OCTET STRING (SIZE(0..32))
      MAX-ACCESS read-create
      STATUS     current
      DESCRIPTION
             "Description of the Net User entry."
      ::= { bsnLocalNetUserEntry 4 }

bsnLocalNetUserLifetime OBJECT-TYPE
      SYNTAX     TimeInterval(0 | 6000..259200000)
      MAX-ACCESS read-create
      STATUS     current
      DESCRIPTION
              "This object indicates the lifetime of an
              user account expressed in hundredths of a second.

              Lifetime period other than 0 will make it a guest-user.
              Minimum value for guest user is 60 seconds (6000).

              Once configured as non-guest user can not be change 
              to guest user and vice-versa. Default value is for  
              a day and max lifetime is 259200000(30 days). WLANIds, 
              which have webauth policy are valid for guest access
              user. "
      DEFVAL  { 8640000 }
      ::= { bsnLocalNetUserEntry 5 }

bsnLocalNetUserStartTime OBJECT-TYPE
      SYNTAX     TimeTicks
      MAX-ACCESS read-only
      STATUS     current
      DESCRIPTION
              "This object indicates the time when the guest user
              account was created and expressed as the number of
              seconds elapsed since 1st Jan, 1970. " 
      ::= { bsnLocalNetUserEntry 6 }

bsnLocalNetUserRemainingTime OBJECT-TYPE
      SYNTAX     TimeInterval
      MAX-ACCESS read-only
      STATUS     current
      DESCRIPTION
              "This object indicates the remaining session time
              for the guest user in hundredths of a second. " 
      ::= { bsnLocalNetUserEntry 7}

bsnLocalNetUserRowStatus OBJECT-TYPE
      SYNTAX     RowStatus
      MAX-ACCESS read-create
      STATUS     current
      DESCRIPTION
             "Row Status"
      ::= { bsnLocalNetUserEntry 24 }

-- *******************************************************************
-- bsnLocalManagementUserTable
-- *******************************************************************

bsnLocalManagementUserTable OBJECT-TYPE
      SYNTAX     SEQUENCE OF BsnLocalManagementUserEntry
      MAX-ACCESS not-accessible
      STATUS     current
      DESCRIPTION
            "The (conceptual) table listing Local Management Users"
      ::= { bsnAAA 11 }


bsnLocalManagementUserEntry OBJECT-TYPE
      SYNTAX     BsnLocalManagementUserEntry
      MAX-ACCESS not-accessible
      STATUS     current
      DESCRIPTION
            "...."
      INDEX      { bsnLocalManagementUserName }
      ::= { bsnLocalManagementUserTable 1 }

BsnLocalManagementUserEntry ::= SEQUENCE {
          bsnLocalManagementUserName            OCTET STRING,
          bsnLocalManagementUserPassword        OCTET STRING,
          bsnLocalManagementUserAccessMode      INTEGER,
          bsnLocalManagementUserRowStatus       RowStatus
}

bsnLocalManagementUserName OBJECT-TYPE
      SYNTAX     OCTET STRING (SIZE(1..24))
      MAX-ACCESS read-create
      STATUS     current
      DESCRIPTION
             "User Name"
      ::= { bsnLocalManagementUserEntry 1 }

bsnLocalManagementUserPassword OBJECT-TYPE
      SYNTAX     OCTET STRING (SIZE(1..24))
      MAX-ACCESS read-create
      STATUS     current
      DESCRIPTION
             "User Password"
      ::= { bsnLocalManagementUserEntry 2 }

bsnLocalManagementUserAccessMode OBJECT-TYPE
      SYNTAX     INTEGER { readOnly (1) , readWrite (2)}
      MAX-ACCESS read-create
      STATUS     current
      DESCRIPTION
             "User Access Mode."
      ::= { bsnLocalManagementUserEntry 3 }

bsnLocalManagementUserRowStatus OBJECT-TYPE
      SYNTAX     RowStatus
      MAX-ACCESS read-create
      STATUS     current
      DESCRIPTION
             "Row Status"
      ::= { bsnLocalManagementUserEntry 23 }

-- *******************************************************************
-- bsnAclTable
-- *******************************************************************

bsnAclTable OBJECT-TYPE
      SYNTAX     SEQUENCE OF BsnAclEntry
      MAX-ACCESS not-accessible
      STATUS     current
      DESCRIPTION
            "The table listing ACLs (Access Control Lists) on the 
             Switch."
      ::= { bsnAAA 7 }


bsnAclEntry OBJECT-TYPE
      SYNTAX     BsnAclEntry
      MAX-ACCESS not-accessible
      STATUS     current
      DESCRIPTION
            "...."
      INDEX      { bsnAclName }
      ::= { bsnAclTable 1 }

BsnAclEntry ::= SEQUENCE {
                bsnAclName            OCTET STRING,
                bsnAclApplyMode       INTEGER,
                bsnAclRowStatus       RowStatus
           }

bsnAclName OBJECT-TYPE
      SYNTAX     OCTET STRING (SIZE(1..32))
      MAX-ACCESS read-create
      STATUS     current
      DESCRIPTION
             "Name of the Access Control List."
      ::= { bsnAclEntry 1 }

bsnAclApplyMode OBJECT-TYPE
      SYNTAX     INTEGER { notapplied (0) , applied (1)}
      MAX-ACCESS read-only
      STATUS     current
      DESCRIPTION
             "The apply mode of the ACL on the switch. Mode value 
              'applied' means the ACL has been applied on the switch."
      ::= { bsnAclEntry 2 }

bsnAclRowStatus OBJECT-TYPE
      SYNTAX     RowStatus
      MAX-ACCESS read-create
      STATUS     current
      DESCRIPTION
             "Row Status of the ACL."
      ::= { bsnAclEntry 20 }


-- *******************************************************************
-- bsnAclRuleTable
-- *******************************************************************

bsnAclRuleTable OBJECT-TYPE
      SYNTAX     SEQUENCE OF BsnAclRuleEntry
      MAX-ACCESS not-accessible
      STATUS     current
      DESCRIPTION
            "The table listing Acl Rules(Access Control List Entries) 
             on the ACL with name bsnAclName."
      ::= { bsnAAA 8 }

bsnAclRuleEntry OBJECT-TYPE
      SYNTAX     BsnAclRuleEntry
      MAX-ACCESS not-accessible
      STATUS     current
      DESCRIPTION
            "...."
      INDEX      { bsnAclName, bsnAclRuleIndex }
      ::= { bsnAclRuleTable 1 }

BsnAclRuleEntry ::= SEQUENCE {
                    bsnAclRuleIndex                    Unsigned32,
                    bsnAclRuleAction                   INTEGER,
                    bsnAclRuleDirection                INTEGER,
                    bsnAclRuleSourceIpAddress          IpAddress,
                    bsnAclRuleSourceIpNetmask          IpAddress,
                    bsnAclRuleDestinationIpAddress     IpAddress,
                    bsnAclRuleDestinationIpNetmask     IpAddress,
                    bsnAclRuleProtocol                 Unsigned32,
                    bsnAclRuleStartSourcePort          Unsigned32,
                    bsnAclRuleEndSourcePort            Unsigned32,
                    bsnAclRuleStartDestinationPort     Unsigned32,
                    bsnAclRuleEndDestinationPort       Unsigned32,
                    bsnAclRuleDscp                     Unsigned32,
                    bsnAclNewRuleIndex                 Unsigned32,
                    bsnAclRuleRowStatus                RowStatus
            }

bsnAclRuleIndex OBJECT-TYPE
      SYNTAX Unsigned32(1..64)
      MAX-ACCESS read-create
      STATUS     current
      DESCRIPTION
             "Index of the ACL rule. This can be updated to reset the 
              sequence of the rules of an ACL."
      ::= { bsnAclRuleEntry 2 }

bsnAclRuleAction OBJECT-TYPE
      SYNTAX     INTEGER { deny (0) , permit (1)}
      MAX-ACCESS read-create
      STATUS     current
      DESCRIPTION
             "The permission mode of a rule."
      DEFVAL { deny }
      ::= { bsnAclRuleEntry 3 }

bsnAclRuleDirection OBJECT-TYPE
      SYNTAX     INTEGER { inbound (0), outbound(1), any (2) }
      MAX-ACCESS read-create
      STATUS     current
      DESCRIPTION
             "The direction of the packet to which the rule may be 
              applied."
      DEFVAL { any }
      ::= { bsnAclRuleEntry 4 }

bsnAclRuleSourceIpAddress OBJECT-TYPE
         SYNTAX      IpAddress
         MAX-ACCESS  read-create
         STATUS      current
         DESCRIPTION
                "Source IP Address of the ACL rule. A value 0 implies 
                 any source address."
         DEFVAL { '00000000'H }
         ::= { bsnAclRuleEntry 5 }

bsnAclRuleSourceIpNetmask OBJECT-TYPE
         SYNTAX      IpAddress
         MAX-ACCESS  read-create
         STATUS      current
         DESCRIPTION
                "Source IP Netmask of the ACL rule.  A value 0 
                 implies any source mask."
         DEFVAL { '00000000'H }
         ::= { bsnAclRuleEntry 6 }

bsnAclRuleDestinationIpAddress OBJECT-TYPE
         SYNTAX      IpAddress
         MAX-ACCESS  read-create
         STATUS      current
         DESCRIPTION
                "Destination IP Address of the ACL rule. A value 0 
                 implies any destination address."
         DEFVAL { '00000000'H }
         ::= { bsnAclRuleEntry 7 }

bsnAclRuleDestinationIpNetmask OBJECT-TYPE
         SYNTAX      IpAddress
         MAX-ACCESS  read-create
         STATUS      current
         DESCRIPTION
                "Destination Netmask of the ACL rule. A value 0 
                 implies any destination mask."
         DEFVAL { '00000000'H }
         ::= { bsnAclRuleEntry 8 }

bsnAclRuleProtocol OBJECT-TYPE
        SYNTAX Unsigned32(0..256)
        MAX-ACCESS read-create
        STATUS current
        DESCRIPTION
                "Protocol of the packet. It can be either of the pre 
                 specified protocols like TCP, UDP, ICMP, ESP, AH, GRE,
                 IP, Ethernet Over IP, OSPF or any number between 0 
                 and 255. A value 256 implies that this rule applies 
                 to 'Any' protocol."
        DEFVAL { 256 }
        ::= { bsnAclRuleEntry 9 }

bsnAclRuleStartSourcePort OBJECT-TYPE
        SYNTAX Unsigned32(0..65535)
        MAX-ACCESS read-create
        STATUS current
        DESCRIPTION
                "Source Port of the packet. It can be either of the 
                 pre specified ports like HTTP, HTTPS, Telnet, RADIUS 
                 etc or any number between 0 and 65535. A value 65536 
                 implies that this rule applies to 'Any' source port.
                 This value can be set only if the protocol is set to 
                 TCP or UDP.  Otherwise the value is set to Any(65536)"
        DEFVAL { 0 }
        ::= { bsnAclRuleEntry 10 }

bsnAclRuleEndSourcePort OBJECT-TYPE
        SYNTAX Unsigned32(0..65535)
        MAX-ACCESS read-create
        STATUS current
        DESCRIPTION
                "Source Port of the packet. It can be either of the 
                 pre specified ports like HTTP, HTTPS, Telnet, RADIUS 
                 etc or any number between 0 and 65535.
                 A value 65536 implies that this rule applies to 'Any'
                 source port.  This value can be set only if the 
                 protocol is set to TCP or UDP.
                 Otherwise the value is set to Any(65536)"
        DEFVAL { 65535 }
        ::= { bsnAclRuleEntry 11 }

bsnAclRuleStartDestinationPort OBJECT-TYPE
        SYNTAX Unsigned32(0..65535)
        MAX-ACCESS read-create
        STATUS current
        DESCRIPTION
                "Destination Port of the packet. It can be either of 
                 the pre specified ports like HTTP, HTTPS, Telnet, 
                 RADIUS etc or any number between 0 and 65535.
                 A value 65536 implies that this rule aplpies to 'Any'
                 Destination port. This value can be set only if the 
                 protocol is set to TCP or UDP.  Otherwise the value is
                 set to Any(65536)"
        DEFVAL { 0 }
        ::= { bsnAclRuleEntry 12 }

bsnAclRuleEndDestinationPort OBJECT-TYPE
        SYNTAX Unsigned32(0..65535)
        MAX-ACCESS read-create
        STATUS current
        DESCRIPTION
                "Destination Port of the packet. It can be either of 
                 the pre specified ports like HTTP, HTTPS, Telnet, 
                 RADIUS etc or any number between 0 and 65535.
                 A value 65536 implies that this rule aplpies to 'Any'
                 Destination port. This value can be set only if the 
                 protocol is set to TCP or UDP.  Otherwise the value is
                 set to Any(65536)"
        DEFVAL { 65535 }
        ::= { bsnAclRuleEntry 13 }

bsnAclRuleDscp OBJECT-TYPE
        SYNTAX Unsigned32(0..256)
        MAX-ACCESS read-create
        STATUS current
        DESCRIPTION
                "DSCP value of the rule. A value 256 implies Any"
        DEFVAL { 256 }
        ::= { bsnAclRuleEntry 14 }

bsnAclNewRuleIndex OBJECT-TYPE
      SYNTAX Unsigned32(1..64)
      MAX-ACCESS read-create
      STATUS     current
      DESCRIPTION
             "New Index of the ACL rule. This attribute should be 
              updated if the requirement is to reset the sequence of 
              the rules of an ACL. A read on this will not yield 
              anything."
      ::= { bsnAclRuleEntry 15 }

bsnAclRuleRowStatus OBJECT-TYPE
      SYNTAX     RowStatus
      MAX-ACCESS read-create
      STATUS     current
      DESCRIPTION
             "Row Status of the ACL Rule."
      ::= { bsnAclRuleEntry 40 }


-- *******************************************************************
-- bsnAAA common attributes
-- *******************************************************************

bsnRadiusAuthKeyWrapEnable     OBJECT-TYPE
      SYNTAX            TruthValue
      MAX-ACCESS        read-write
      STATUS            current
      DESCRIPTION
          " When keyWrap is enable then for 801.1X and 802.11i 
            client Authentication, request is sent to those 
            radius servers which has KEK and MACK keys are configured.
          
            Radius servers are widely used for user authentications.
            In 802.11i and 802.1X type authentication, the controller
            recives Pairwise Master KEy(PMK) from RADIUS sever using
            vendor specific RADIUS attributes, which uses MPPE RFC3078.
            Since MPPE uses RC4 algorithm to provide data 
            confidentiality, it is not FIPS approved. For this RADIUS 
            key WRAP attributes, bsnRadiusAuthServerKeyWrap 
            and bsnRadiusAuthServerKeyWrapMACKkey have been added, 
            which are used to securely transfer encryption keys using 
            non-proprietary techniques."
      DEFVAL { false }
      ::= { bsnAAA 12 }


bsnRadiusAuthCacheCredentialsLocally  OBJECT-TYPE
      SYNTAX INTEGER { disable(0),enable (1)}
      MAX-ACCESS read-write
      STATUS current
      DESCRIPTION
            "Enable or disable caching of credentials locally for 
             RADIUS Auth servers.  This is used when a client uses a 
             one time password authentication scheme."
      ::= { bsnAAA 14 }


bsnAAAMacDelimiter OBJECT-TYPE
      SYNTAX     INTEGER { noDelimiter (0),
                 colon(1), hyphen (2), singleHyphen (3) }
      MAX-ACCESS read-write
      STATUS     current
      DESCRIPTION
             "The delimiter to be used for mac filtering. It can be 
              colon as in xx:xx:xx:xx:xx:xx or hyphen as in 
              xx-xx-xx-xx-xx-xx or single hyphen as in 
              xxxxxx-xxxxxx or no delimiter as in xxxxxxxxxxxx."
      ::= { bsnAAA 15 }

bsnAAARadiusCompatibilityMode OBJECT-TYPE
      SYNTAX     INTEGER { ciscoACS (0), orinocoRadius(1), other (2) }
      MAX-ACCESS read-write
      STATUS     current
      DESCRIPTION
             "The required compatibility mode for MAC filtering. For 
              ciscoACS, the expected MAC delimiter setting is colon and
              for orinocoRadius, it is singleHyphen."
      ::= { bsnAAA 16 }

bsnAAARadiusCallStationIdType OBJECT-TYPE
      SYNTAX     INTEGER { ipAddr (0), macAddr(1), apMacAddress(2)}
      MAX-ACCESS read-write
      STATUS     current
      DESCRIPTION
             "This attribute configures the call station ID information
              sent in RADIUS messages. The value undefined cannot be 
              set during the write operation."
      ::= { bsnAAA 17 }

bsnAAALocalDatabaseSize OBJECT-TYPE
      SYNTAX Integer32 (512..2048)
      MAX-ACCESS read-write
      STATUS     current
      DESCRIPTION
             "This attribute is the total number of entries permitted 
              in the local users database. This is the combined total 
              of entries for Local Management Users, Local Net Users, 
              Disabled Clients (previously known as blacklistclients 
              and the MAC Filters. If the database size limit is 
              reached, no more entries in any of these user lists are 
              allowed to be created. To continue creating more entries,
              one should increase the size of the database. This value 
              is applied on reboot and then matches the 
              bsnAACurrentLocalDatabaseSize."
      ::= { bsnAAA 20 }

bsnAAACurrentLocalDatabaseSize OBJECT-TYPE
      SYNTAX Integer32 (512..2048)
      MAX-ACCESS read-only
      STATUS     current
      DESCRIPTION
             "This attribute is the maximum number of entries in the 
              local users database that is effective currently.
              This is the combined total of entries for Local 
              Management Users, Local Net Users, Disabled Clients
              (previously known as blacklist clients) and the MAC 
              Filters."
      ::= { bsnAAA 21 }

-- *******************************************************************
-- bsnBlackListClientTable
-- *******************************************************************

bsnBlackListClientTable OBJECT-TYPE
      SYNTAX     SEQUENCE OF BsnBlackListClientEntry
      MAX-ACCESS not-accessible
      STATUS     current
      DESCRIPTION
            "The table listing Wlan Black Listed Clients"
      ::= { bsnAAA 6 }


bsnBlackListClientEntry OBJECT-TYPE
      SYNTAX     BsnBlackListClientEntry
      MAX-ACCESS not-accessible
      STATUS     current
      DESCRIPTION
            "...."
      INDEX      { bsnBlackListClientMacAddress }
      ::= { bsnBlackListClientTable 1 }

BsnBlackListClientEntry ::= SEQUENCE {
                bsnBlackListClientMacAddress         OCTET STRING,
                bsnBlackListClientDescription        OCTET STRING,
                bsnBlackListClientRowStatus          RowStatus
       }

bsnBlackListClientMacAddress OBJECT-TYPE
      SYNTAX     OCTET STRING (SIZE(1..12))
      MAX-ACCESS read-create
      STATUS     current
      DESCRIPTION
             "Black Listed Client MAC Address"
      ::= { bsnBlackListClientEntry 1 }

bsnBlackListClientDescription OBJECT-TYPE
      SYNTAX     OCTET STRING (SIZE(0..32))
      MAX-ACCESS read-create
      STATUS     current
      DESCRIPTION
             "Black Listed Client Description "
      ::= { bsnBlackListClientEntry 2 }

bsnBlackListClientRowStatus OBJECT-TYPE
      SYNTAX     RowStatus
      MAX-ACCESS read-create
      STATUS     current
      DESCRIPTION
             "Row Status"
      ::= { bsnBlackListClientEntry 22 }

--*******************************************************************
-- * Begin of bsnExternalPolicyServerTable
--*******************************************************************
bsnExternalPolicyServerTable OBJECT-TYPE
      SYNTAX     SEQUENCE OF BsnExternalPolicyServerEntry
      MAX-ACCESS not-accessible
      STATUS     obsolete
      DESCRIPTION
            "The (conceptual) table listing the External Policy
             servers with which client share a secret."
      ::= { bsnAAA 19 }


bsnExternalPolicyServerEntry OBJECT-TYPE
      SYNTAX     BsnExternalPolicyServerEntry
      MAX-ACCESS not-accessible
      STATUS     obsolete
      DESCRIPTION
            "An entry (conceptual row) representing an External 
             policy server with which the client shares
             a secret."
      INDEX      { bsnExternalPolicyServerIndex }
      ::= { bsnExternalPolicyServerTable 1 }

BsnExternalPolicyServerEntry ::= SEQUENCE {
      bsnExternalPolicyServerIndex                     Integer32,
      bsnExternalPolicyServerAddress                   IpAddress,
      bsnExternalPolicyServerPortNumber                Integer32,
      bsnExternalPolicyServerKey                       OCTET STRING,
      bsnExternalPolicyServerAdminStatus               INTEGER,
      bsnExternalPolicyServerConnectionStatus          INTEGER,
      bsnExternalPolicyServerRowStatus                 RowStatus
}

bsnExternalPolicyServerIndex OBJECT-TYPE
      SYNTAX     Integer32 (0..2)
      MAX-ACCESS read-create
      STATUS     obsolete
      DESCRIPTION
             "A number uniquely identifying each External
             Policy server with which this client
             communicates."
      ::= { bsnExternalPolicyServerEntry 1 }

bsnExternalPolicyServerAddress OBJECT-TYPE
      SYNTAX     IpAddress
      MAX-ACCESS read-create
      STATUS     obsolete
      DESCRIPTION
            "The IP address of the External Policy server
             referred to in this table entry."
      ::= { bsnExternalPolicyServerEntry 2 }

bsnExternalPolicyServerPortNumber  OBJECT-TYPE
      SYNTAX Integer32 (0..65535)
      MAX-ACCESS read-create
      STATUS obsolete
      DESCRIPTION
            "The UDP port the client is using to send requests to
             this server."
      ::= { bsnExternalPolicyServerEntry 3 }

bsnExternalPolicyServerKey OBJECT-TYPE
        SYNTAX  OCTET STRING (SIZE(0..16))
        MAX-ACCESS  read-create
        STATUS  obsolete
        DESCRIPTION
                "The authentication and encryption key shared between
                the client and this External Policy Server."
        DEFVAL { "" }
        ::= { bsnExternalPolicyServerEntry 4 }

bsnExternalPolicyServerAdminStatus  OBJECT-TYPE
      SYNTAX INTEGER { disable(0),enable (1)}
      MAX-ACCESS read-create
      STATUS obsolete
      DESCRIPTION
            "Server enable or disable status."
      ::= { bsnExternalPolicyServerEntry 5 }

bsnExternalPolicyServerConnectionStatus  OBJECT-TYPE
      SYNTAX INTEGER { disconnected(0),connected (1)}
      MAX-ACCESS read-only
      STATUS obsolete
      DESCRIPTION
            "Server enable or disable status."
      ::= { bsnExternalPolicyServerEntry 6 }
      
bsnExternalPolicyServerRowStatus  OBJECT-TYPE
      SYNTAX RowStatus
      MAX-ACCESS read-create
      STATUS obsolete
      DESCRIPTION
    " Row Status for creation/deletion"
      ::= { bsnExternalPolicyServerEntry 26 }

bsnExternalPolicyServerAclName OBJECT-TYPE
      SYNTAX DisplayString (SIZE(0..32))     
      MAX-ACCESS read-write
      STATUS     current
      DESCRIPTION
             "This attribute configures the ACL Name for External 
              Policy Servers"
      ::= { bsnAAA 18 }

bsnAcceptSelfSignedCertificate OBJECT-TYPE
        SYNTAX INTEGER { disable(0), enable(1) }
        MAX-ACCESS read-write
        STATUS current
        DESCRIPTION
            "This flag specifies if controller will accept Self Signed
             Certificate from AP as part of authorization."
        ::= { bsnGlobalDot11Config 48 }

bsnSystemClockTime OBJECT-TYPE 
         SYNTAX     Unsigned32 
         UNITS      "seconds"
         MAX-ACCESS read-only 
         STATUS     current 
         DESCRIPTION 
             "This object represents the current clock time 
              of the controller and expressed as the number of 
              seconds elapsed since 00:00:00 on 
              January 1, 1970, Coordinated Universal Time (UTC). " 
         ::= { bsnGlobalDot11Config 49 } 


-- *******************************************************************
-- bsnAPAuthorizationTable
-- *******************************************************************

bsnAPAuthorizationTable OBJECT-TYPE
      SYNTAX     SEQUENCE OF BsnAPAuthorizationEntry
      MAX-ACCESS not-accessible
      STATUS     current
      DESCRIPTION
            "The table listing AP Authorization entries"
      ::= { bsnAAA 22 }

bsnAPAuthorizationEntry OBJECT-TYPE
      SYNTAX     BsnAPAuthorizationEntry
      MAX-ACCESS not-accessible
      STATUS     current
      DESCRIPTION
            "BsnAPAuthorizationEntry"
      INDEX      { bsnAPAuthMacAddress }
      ::= { bsnAPAuthorizationTable 1 }

BsnAPAuthorizationEntry ::= SEQUENCE {
                bsnAPAuthMacAddress         OCTET STRING,
                bsnAPAuthCertificateType    INTEGER,
                bsnAPAuthHashKey            OCTET STRING,
                bsnAPAuthRowStatus          RowStatus
}

bsnAPAuthMacAddress OBJECT-TYPE
      SYNTAX     OCTET STRING (SIZE(1..24))
      MAX-ACCESS read-create
      STATUS     current
      DESCRIPTION
             "MAC Address of the AP entry"
      ::= { bsnAPAuthorizationEntry 1 }

bsnAPAuthCertificateType OBJECT-TYPE
      SYNTAX     INTEGER { unknown(0), mic(1), ssc(2) }
      MAX-ACCESS read-create
      STATUS     current
      DESCRIPTION
             "Supported certificate types are MIC and SSC 
              (Self-Signed-Certificate)."
      ::= { bsnAPAuthorizationEntry 2 }

bsnAPAuthHashKey OBJECT-TYPE
      SYNTAX     OCTET STRING (SIZE(0..40))
      MAX-ACCESS read-create
      STATUS     current
      DESCRIPTION
             "SHA1 hash key for SSC certificate validation. 
              It has to be 40 hexa-decimal characters. 
              This is considered when certificate type is SSC."
      ::= { bsnAPAuthorizationEntry 3 }

bsnAPAuthRowStatus OBJECT-TYPE
      SYNTAX     RowStatus
      MAX-ACCESS read-create
      STATUS     current
      DESCRIPTION
             "Row Status"
      ::= { bsnAPAuthorizationEntry 20 }


-- ********************************************************************
-- * Begin of bsnWrasIKECertTable
-- ********************************************************************

bsnWrasIpsecCACertificate OBJECT-TYPE
    SYNTAX  OCTET STRING (SIZE(0..4096))
    MAX-ACCESS  read-only
    STATUS  current
    DESCRIPTION
            ""
    DEFVAL { "" }
    ::= { bsnIpsec 1 }

bsnWrasIpsecCACertificateUpdate OBJECT-TYPE
    SYNTAX  OCTET STRING (SIZE(0..4096))
    MAX-ACCESS  read-write
    STATUS  current
    DESCRIPTION
            "Note this attribute is for updating the certificate
         If you try to read it, it will always be ***"
    DEFVAL { "" }
    ::= { bsnIpsec 2 }

bsnWrasIpsecCertTable OBJECT-TYPE
    SYNTAX  SEQUENCE OF BsnWrasIpsecCertEntry
    MAX-ACCESS  not-accessible
    STATUS  current
    DESCRIPTION
        "A table of Certificates."
    ::= { bsnIpsec 3}

bsnWrasIpsecCertEntry OBJECT-TYPE
    SYNTAX   BsnWrasIpsecCertEntry
    MAX-ACCESS  not-accessible
    STATUS  current
    DESCRIPTION
        "Each entry contains a specific certificate."
    INDEX   { bsnWrasIpsecCertName }
    ::= { bsnWrasIpsecCertTable 1 }

BsnWrasIpsecCertEntry ::=
    SEQUENCE {
    bsnWrasIpsecCertName           DisplayString,
    bsnWrasIpsecCertificateUpdate  OCTET STRING,
    bsnWrasIpsecCertificate        OCTET STRING,
    bsnWrasIpsecCertPassword       OCTET STRING,
    bsnWrasIpsecCertStatus         RowStatus
    }

bsnWrasIpsecCertName OBJECT-TYPE
    SYNTAX  DisplayString (SIZE(0..80))
    MAX-ACCESS read-create
    STATUS  current
    DESCRIPTION
         "The name assigned to this set of IKE Certificates."
    ::= { bsnWrasIpsecCertEntry 1 }


bsnWrasIpsecCertificateUpdate OBJECT-TYPE
    SYNTAX  OCTET STRING (SIZE(0..4096))
    MAX-ACCESS  read-create
    STATUS  current
    DESCRIPTION
            "If you try to read this it will always be ***"
    DEFVAL { "" }
    ::= { bsnWrasIpsecCertEntry 2 }

bsnWrasIpsecCertificate OBJECT-TYPE
    SYNTAX  OCTET STRING (SIZE(0..4096))
    MAX-ACCESS  read-only
    STATUS  current
    DESCRIPTION
            ""
    DEFVAL { "" }
    ::= { bsnWrasIpsecCertEntry 3 }

bsnWrasIpsecCertPassword OBJECT-TYPE
    SYNTAX  OCTET STRING (SIZE(0..1500))
    MAX-ACCESS  read-create
    STATUS  current
    DESCRIPTION
            ""
    DEFVAL { "" }
    ::= { bsnWrasIpsecCertEntry 4 }

bsnWrasIpsecCertStatus OBJECT-TYPE
    SYNTAX  RowStatus
    MAX-ACCESS  read-create
    STATUS  current
    DESCRIPTION
            "A row status type for the IKE Cert Entry."
    ::= { bsnWrasIpsecCertEntry 24 }

-- *************************************************************
-- bsnTrap Object Group
-- *************************************************************

-- *************************************************************
-- bsnTrapControl would specify all the objects that enable/disable the
-- the generation of traps by Airespace Switch
-- *************************************************************

bsnTrapControl OBJECT IDENTIFIER ::= { bsnTrap 1 }
bsnTrapVariable OBJECT IDENTIFIER ::= { bsnTrap 2 }

-- *************************************************************
-- bsnTraps would specify all the possible traps that Airespace Switch
-- would need to generate
-- *************************************************************
bsnTraps OBJECT IDENTIFIER ::= { bsnTrap 3 }


-- *************************************************************
-- Mobile Station related traps and trapControl
-- *************************************************************

bsnDot11StationTrapControlMask OBJECT-TYPE
        SYNTAX   Unsigned32
        MAX-ACCESS   read-write
        STATUS   current
        DESCRIPTION
           "This mask describes what events merit traps to network 
            management. If the bit for a particular event is turned on
            then notification will be generated on event occurence.
                Event                    corresponding bit
                -----                    -----------------
                bsnDot11StationDisassociate           1
                bsnDot11StationDeauthenticate         2
                bsnDot11StationAuthenticateFail       4
                bsnDot11StationAssociateFail          8
                bsnDot11StationBlacklisted            16
       By Default all bits are off.
           "
    DEFVAL {0}
       ::= { bsnTrapControl 1 }

bsnDot11StationDisassociate NOTIFICATION-TYPE
    OBJECTS { bsnStationAPMacAddr,bsnStationAPIfSlotId,
              bsnStationReasonCode,
             bsnStationMacAddress }
    STATUS current
    DESCRIPTION
        "The disassociate notification shall be sent when the Station
        sends a Disassociation frame. The value of the notification
        shall include the MAC address of the MAC to which the 
        Disassociation frame was sent and the reason for the 
        disassociation"
    ::= { bsnTraps 1 }

bsnDot11StationDeauthenticate NOTIFICATION-TYPE
    OBJECTS { bsnStationAPMacAddr,bsnStationAPIfSlotId,
              bsnStationReasonCode,
             bsnStationMacAddress  }
    STATUS current
    DESCRIPTION
        "The deauthenticate notification shall be sent when the Station
        sends a Deauthentication frame. The value of the notification
        shall include the MAC address of the MAC to which the
        Deauthentication frame was sent and the reason for the
        deauthentication."
    ::= { bsnTraps 2 }

bsnDot11StationAuthenticateFail NOTIFICATION-TYPE
    OBJECTS { bsnStationAPMacAddr,bsnStationAPIfSlotId,
              bsnStationReasonCode,
             bsnStationMacAddress  }
    STATUS current
    DESCRIPTION
        "The authenticate failure notification shall be sent when the 
         Station sends an Authentication frame with a status code other
         than 'successful'. The value of the notification shall include
         the MAC address of the MAC to which the Authentication
         frame was sent and the reason for the authentication failure."
    ::= { bsnTraps 3 }

bsnDot11StationAssociateFail NOTIFICATION-TYPE
    OBJECTS {  bsnStationAPMacAddr,bsnStationAPIfSlotId,
              bsnStationReasonCode,
             bsnStationMacAddress }
    STATUS current
    DESCRIPTION
        "The associate failure notification shall be sent when the 
         Station sends an Association frame with a status code other 
         than 'successful'. The value of the notification
         shall include the MAC address of the MAC to which the 
         Authentication frame was sent and the reason for the 
         authentication failure."
    ::= { bsnTraps 4 }

bsnDot11StationBlacklisted NOTIFICATION-TYPE
    OBJECTS {  bsnStationAPMacAddr, bsnStationAPIfSlotId,
               bsnStationBlacklistingReasonCode,
               bsnStationMacAddress }
    STATUS current
    DESCRIPTION
        "The station blacklisted notification shall be sent when the 
         client is blacklisted.  The reason could be repeated auth or 
         association failures or IP Address theft.
         The value of the notification shall include the MAC address 
         of the MAC to which the Authentication frame was sent, the 
         MAC and Slot Id of AP that client was associated to and the 
         reason for black listing."
    ::= { bsnTraps 52 }

bsnDot11StationAssociate NOTIFICATION-TYPE
    OBJECTS {  bsnStationAPMacAddr,bsnStationAPIfSlotId,
             bsnStationMacAddress, bsnStationUserName }
    STATUS current
    DESCRIPTION
        "The associate notification shall be sent when any of the 
         watchlisted clients(present on at least one watch list)
         associates with an AP. The value of the notification
         shall include the MAC address and the Slot ID of the radio 
         to which the station Associated."
    ::= { bsnTraps 53 }

-- *************************************************************
-- Airespace AP related Traps
-- *************************************************************

bsnAPTrapControlMask OBJECT-TYPE
        SYNTAX   Unsigned32
        MAX-ACCESS   read-write
        STATUS   current
        DESCRIPTION
           "This mask describes what events merit traps to network 
            management. If the bit for a particular event is turned on
            then notification will be generated on event occurance.
                Event                       corresponding bit
                -----                       -----------------
                bsnAPAssociate/Disassociate      1
                bsnAPIfUp/Down                   4

            By Default all bits are on."
       DEFVAL {63}
       ::= { bsnTrapControl 2 }

bsnAPUp NOTIFICATION-TYPE
    OBJECTS { bsnAPDot3MacAddress }
    STATUS current
    DESCRIPTION
        "When Airespace AP operation status goes up this trap will be 
         sent"
    ::= { bsnTraps 5 }

bsnAPDown NOTIFICATION-TYPE
    OBJECTS { bsnAPDot3MacAddress }
    STATUS current
    DESCRIPTION
        "When Airespace AP operation status goes down this trap will be
         sent"
    ::= { bsnTraps 6 }

bsnAPAssociated NOTIFICATION-TYPE
    OBJECTS { bsnAPMacAddrTrapVariable,bsnAPPortNumberTrapVariable }
    STATUS current
    DESCRIPTION
        "When Airespace AP Associates to a Airespace Switch, AP 
         associated notification will be sent with dot3 MAC address of 
         Airespace AP.This will help management system to discover 
         Airespace AP and add to system."
    ::= { bsnTraps 7 }

bsnAPDisassociated NOTIFICATION-TYPE
    OBJECTS { bsnAPMacAddrTrapVariable }
    STATUS current
    DESCRIPTION
        "When Airespace AP disassociates from Airespace Switch, AP 
         disassociated notification will be sent with dot3 MAC address
         of Airespace AP management system to remove Airespace AP from
         this Airespace Switch"
    ::= { bsnTraps 8 }

bsnAPIfUp NOTIFICATION-TYPE
    OBJECTS { bsnAPDot3MacAddress, bsnAPIfSlotId, 
              bsnAPPortNumber, bsnAPIfUpDownCause }
    STATUS current
    DESCRIPTION
        "When Airespace AP's interface's operation status goes up this
         trap will be sent"
    ::= { bsnTraps 9 }

bsnAPIfDown NOTIFICATION-TYPE
    OBJECTS { bsnAPDot3MacAddress, bsnAPIfSlotId,
              bsnAPAdminStatus, bsnAPIfAdminStatus, 
              bsnAPIfUpDownCause }
    STATUS current
    DESCRIPTION
        "When Airespace AP's interface's operation status goes down 
         this trap will be sent."
    ::= { bsnTraps 10 }

-- *************************************************************
-- RRM related trapControl and traps
-- *************************************************************

-- *************************************************************
-- Whenever LOAD, NOISE, INTERFERENCE, COVERAGE Profile state changes
-- from PASS to FAIL for Airespace AP IF, notification will be sent, if
-- configured to do so.
-- *************************************************************

bsnAPProfileTrapControlMask OBJECT-TYPE
        SYNTAX   Unsigned32
        MAX-ACCESS   read-write
        STATUS   current
        DESCRIPTION
           "This mask describes what events merit traps to network 
            management. If the bit for a particular event is turned 
            on then notification will be generated on event occurance.
                Event                    corresponding bit
                -----                    -----------------
                LoadProfileFail                  1
                NoiseProfileFail                 2
                InterferenceProfileFail          4
                CoverageProfileFailed            8
           "
       ::= { bsnTrapControl 3 }


bsnAPLoadProfileFailed NOTIFICATION-TYPE
    OBJECTS { bsnAPDot3MacAddress, bsnAPIfSlotId }
    STATUS current
    DESCRIPTION
        "When LOAD Profile state changes from PASS to FAIL, 
         notification will be sent with Dot3 MAC address of Airespace 
         AP and slot ID of Airespace AP IF. This trap sending can be 
         enable/disable using bsnRrmProfileTrapControlFlag "
    ::= { bsnTraps 11 }

bsnAPNoiseProfileFailed NOTIFICATION-TYPE
    OBJECTS { bsnAPDot3MacAddress, bsnAPIfSlotId }
    STATUS current
    DESCRIPTION
        "When Noise Profile state changes from PASS to FAIL, 
         notification will be sent with Dot3 MAC address of Airespace 
         AP and slot ID of Airespace AP IF. This trap sending can be 
         enable/disable using bsnRrmProfileTrapControlFlag "
    ::= { bsnTraps 12 }

bsnAPInterferenceProfileFailed NOTIFICATION-TYPE
    OBJECTS { bsnAPDot3MacAddress, bsnAPIfSlotId }
    STATUS current
    DESCRIPTION
        "When Interference Profile state changes from PASS to FAIL,
         notification will be sent with Dot3 MAC address of Airespace 
         AP and slot ID of Airespace AP IF. This trap sending can be 
         enable/disable using bsnRrmProfileTrapControlFlag "
    ::= { bsnTraps 13 }

-- *************************************************************
-- extra trap variables definining here
-- *************************************************************

bsnAPMacAddrTrapVariable OBJECT-TYPE
    SYNTAX  MacAddress
    MAX-ACCESS  accessible-for-notify
    STATUS  current
    DESCRIPTION
            ""
    ::= { bsnTrapVariable 20 }


bsnAPNameTrapVariable OBJECT-TYPE
    SYNTAX  DisplayString
    MAX-ACCESS  accessible-for-notify
    STATUS  current
    DESCRIPTION
            ""
    ::= { bsnTrapVariable 21 }

bsnAPSlotIdTrapVariable OBJECT-TYPE
    SYNTAX Integer32
    MAX-ACCESS  accessible-for-notify
    STATUS current
    DESCRIPTION
        "Number of Radio Interfaces on the Airespace AP."
    ::= {  bsnTrapVariable 22 }

bsnAPChannelNumberTrapVariable OBJECT-TYPE
    SYNTAX Integer32
    MAX-ACCESS  accessible-for-notify
    STATUS current
    DESCRIPTION
    ""
    ::= {  bsnTrapVariable 23 }


bsnAPCoverageThresholdTrapVariable OBJECT-TYPE
    SYNTAX Integer32
    MAX-ACCESS  accessible-for-notify
    STATUS current
    DESCRIPTION
    ""
    ::= {  bsnTrapVariable 24 }

bsnAPCoverageFailedClients OBJECT-TYPE
    SYNTAX Integer32
    MAX-ACCESS  accessible-for-notify
    STATUS current
    DESCRIPTION 
    ""
    ::= {  bsnTrapVariable 25 }

bsnAPCoverageTotalClients OBJECT-TYPE
    SYNTAX Integer32
    MAX-ACCESS  accessible-for-notify
    STATUS current
    DESCRIPTION 
    ""
    ::= {  bsnTrapVariable 26 }

bsnClientMacAddr OBJECT-TYPE
    SYNTAX MacAddress
    MAX-ACCESS  accessible-for-notify
    STATUS current
    DESCRIPTION 
    ""
    ::= {  bsnTrapVariable 27 }

bsnClientRssi OBJECT-TYPE
    SYNTAX Integer32
    MAX-ACCESS  accessible-for-notify
    STATUS current
    DESCRIPTION
    ""
    ::= {  bsnTrapVariable 28 }

bsnClientSnr OBJECT-TYPE
    SYNTAX Integer32
    MAX-ACCESS  accessible-for-notify
    STATUS current
    DESCRIPTION 
    ""
    ::= {  bsnTrapVariable 29 }

bsnInterferenceEnergyBeforeChannelUpdate OBJECT-TYPE
    SYNTAX Integer32
    MAX-ACCESS  accessible-for-notify
    STATUS current
    DESCRIPTION 
    ""
    ::= {  bsnTrapVariable 30 }

bsnInterferenceEnergyAfterChannelUpdate OBJECT-TYPE
    SYNTAX Integer32
    MAX-ACCESS  accessible-for-notify
    STATUS current
    DESCRIPTION 
    ""
    ::= {  bsnTrapVariable 31 }

bsnAPPortNumberTrapVariable OBJECT-TYPE
    SYNTAX Integer32
    MAX-ACCESS  accessible-for-notify
    STATUS current
    DESCRIPTION
    ""
    ::= {  bsnTrapVariable 32 }

bsnAPCoverageProfileFailed NOTIFICATION-TYPE
    OBJECTS { bsnAPMacAddrTrapVariable,bsnAPNameTrapVariable,
              bsnAPSlotIdTrapVariable,
              bsnAPCoverageThresholdTrapVariable,
              bsnAPCoverageFailedClients,bsnAPCoverageTotalClients,
              bsnClientMacAddr,bsnClientRssi,bsnClientSnr }
    STATUS current
    DESCRIPTION
        "When Coverage Profile state changes from PASS to FAIL, 
         notification will be sent with Dot3 MAC address of Airespace 
         AP and slot ID of Airespace AP IF. This trap sending can be 
         enable/disable using bsnRrmProfileTrapControlFlag "
    ::= { bsnTraps 14 }


bsnAPLoadProfileUpdatedToPass NOTIFICATION-TYPE
    OBJECTS { bsnAPDot3MacAddress, bsnAPIfSlotId }
    STATUS current
    DESCRIPTION
        "When LOAD Profile state changes from FAIL to PASSt this 
         notification will be sent with Dot3 MAC address of Airespace 
         AP and slot ID of Airespace AP IF. This trap sending can be 
         enable/disable using bsnRrmProfileTrapControlFlag "
    ::= { bsnTraps 37 }

bsnAPNoiseProfileUpdatedToPass NOTIFICATION-TYPE
    OBJECTS { bsnAPDot3MacAddress, bsnAPIfSlotId }
    STATUS current
    DESCRIPTION
        "When Noise Profile state changes from FAIL tp PASS, 
         notification will be sent with Dot3 MAC address of Airespace 
         AP and slot ID of Airespace AP IF. This trap sending can be 
         enable/disable using bsnRrmProfileTrapControlFlag "
    ::= { bsnTraps 38 }

bsnAPInterferenceProfileUpdatedToPass NOTIFICATION-TYPE
    OBJECTS { bsnAPDot3MacAddress, bsnAPIfSlotId }
    STATUS current
    DESCRIPTION
        "When Interference Profile state changes from FAIL tp PASS,
         notification will be sent with Dot3 MAC address of Airespace 
         AP and slot ID of Airespace AP IF. This trap sending can be 
         enable /disable using bsnRrmProfileTrapControlFlag "
    ::= { bsnTraps 39 }

bsnAPCoverageProfileUpdatedToPass NOTIFICATION-TYPE
    OBJECTS { bsnAPDot3MacAddress,bsnAPIfSlotId}
    STATUS current
    DESCRIPTION
        "When Coverage Profile state changes from FAIL tp PASS, 
         notification will be sent with Dot3 MAC address of Airespace 
         AP and slot ID of Airespace AP IF. This trap sending can be 
         enable/disable using bsnRrmProfileTrapControlFlag "
    ::= { bsnTraps 40 }

bsnAPParamUpdateTrapControlMask OBJECT-TYPE
        SYNTAX   Unsigned32
        MAX-ACCESS   read-write
        STATUS   current
        DESCRIPTION
           "Mac Parameters are updated for a Airespace AP interface 
            whenever Dynamic Algorithm are run. This mask describes 
            what update events merit traps to network management. If 
            the bit for a particular event is turned on then 
            notification will be generated on event occurance.
                Event                    corresponding bit
                -----                    -----------------
                TxPowerChange                  1
                ChannelChange                  2
                AntennaChange                  4
                RTSCTSThresholdChange          8
                EDThresholdChange              16
                FragmentationThresholdChange   32
           "
       ::= { bsnTrapControl 4 }

bsnAPCurrentTxPowerChanged NOTIFICATION-TYPE
    OBJECTS { bsnAPDot3MacAddress, bsnAPIfSlotId,
              bsnAPIfPhyTxPowerLevel }
    STATUS current
    DESCRIPTION
        "Whenever dynamic algorithms are running and 
         bsnAPIfPhyPowerAutomaticOn is true, Airespace AP Interface's 
         CurrentTxPower might get updated by algorithm. When
         this occurs notification will be sent with Dot3 MAC address of
         Airespace AP and slot ID of Airespace AP IF along with the 
         currentTxPower for this Airespace AP IF"
    ::= { bsnTraps 15 }

bsnAPCurrentChannelChanged NOTIFICATION-TYPE
    OBJECTS { bsnAPMacAddrTrapVariable,bsnAPSlotIdTrapVariable,
              bsnAPChannelNumberTrapVariable,
              bsnInterferenceEnergyBeforeChannelUpdate,
              bsnInterferenceEnergyAfterChannelUpdate }
    STATUS current
    DESCRIPTION
        "Whenever dynamic algorithms are running and 
         bsnAPIfPhyChannelAutomaticOn is true, Airespace AP 
         Interface's CurrentChannel might get updated by algorithm. 
         When this occurs notification will be sent with Dot3 MAC 
         address of Airespace AP and slot ID of Airespace AP IF along 
         with the currentChannel for this Airespace AP IF"
    ::= { bsnTraps 16 }


-- *************************************************************
-- Also, when dynamic grouping is done and new Group leader is choosen
-- NMS needs to be informed so that necessary updates can be done in
-- NMS.
-- *************************************************************

bsnRrmDot11aGroupingDone NOTIFICATION-TYPE
    OBJECTS { bsnRrmDot11aGroupLeaderMacAddr }
    STATUS current
    DESCRIPTION
        "When Grouping is done, this notification will be sent from the
         previous Group Leader where grouping algorithm was run. It has
         MAC address of the new Group Leader."
    ::= { bsnTraps 21 }

bsnRrmDot11bGroupingDone NOTIFICATION-TYPE
    OBJECTS { bsnRrmDot11bGroupLeaderMacAddr }
    STATUS current
    DESCRIPTION
        "When Grouping is done, this notification will be sent from the
         previous Group Leader where grouping algorithm was run. It has
         MAC address of the new Group Leader."
    ::= { bsnTraps 22 }

bsnConfigSaveTrapEnable OBJECT-TYPE
        SYNTAX   INTEGER {disable(0),enable(1)}
        MAX-ACCESS   read-write
        STATUS   current
        DESCRIPTION
           "If Rogue AP Detection and Removed Traps need to be sent "
       ::= { bsnTrapControl 9 }

bsnConfigSaved NOTIFICATION-TYPE
    STATUS current
    DESCRIPTION
     "When configuration is save either from CLI or web interface
      This trap will be sent to inform NMS to do refresh"
    ::= { bsnTraps 23 }

bsnDot11EssCreated NOTIFICATION-TYPE
    OBJECTS { bsnDot11EssIndex }
    STATUS current
    DESCRIPTION
        "Whenever a new Ess (WLAN) is created, this notification will 
         be sent along with EssIndex"
    ::= { bsnTraps 24 }

bsnDot11EssDeleted NOTIFICATION-TYPE
    OBJECTS { bsnDot11EssIndex }
    STATUS current
    DESCRIPTION
        "Whenever a Ess (WLAN)is deleted, this notification will be 
         sent along with EssIndex"
    ::= { bsnTraps 25 }
-- *************************************************************
-- AAA Traps
-- *************************************************************

bsnAuthFailureUserName OBJECT-TYPE
    SYNTAX  OCTET STRING (SIZE(0..32))
    MAX-ACCESS  accessible-for-notify
    STATUS  current
    DESCRIPTION
            ""
    ::= { bsnTrapVariable 1 }

bsnAuthFailureUserType OBJECT-TYPE
    SYNTAX  INTEGER { mgmtUser (1), wlanUser (2), macFilter (3)}
    MAX-ACCESS  accessible-for-notify
    STATUS  current
    DESCRIPTION
            ""
    ::= { bsnTrapVariable 2 }

bsnRADIUSServerTrapEnable OBJECT-TYPE
        SYNTAX   INTEGER {disable(0),enable(1)}
        MAX-ACCESS   read-write
        STATUS   current
        DESCRIPTION
        "if RADIUS Server Traps need to be sent "
       ::= { bsnTrapControl 7 }

bsnAuthenticationFailureTrapEnable OBJECT-TYPE
        SYNTAX   INTEGER {disable(0),enable(1)}
        MAX-ACCESS   read-write
        STATUS   current
        DESCRIPTION
           "If Authentication Failure Traps need to be sent "
       ::= { bsnTrapControl 8 }

bsn80211SecurityTrapControlMask OBJECT-TYPE
        SYNTAX   Unsigned32
        MAX-ACCESS   read-write
        STATUS   current
        DESCRIPTION
           "This mask is for Security related trap controls.

                Event                    corresponding bit
                -----                    -----------------
                bsnWepKeyDecryptError           1

             By Default all bits are off."
    DEFVAL {0}
       ::= { bsnTrapControl 10 }

bsnWpsTrapControlEnable OBJECT-TYPE
        SYNTAX   INTEGER {disable(0),enable(1)}
        MAX-ACCESS   read-write
        STATUS   current
        DESCRIPTION
           "This control is for WPS(Wireless Intrusion Protection 
            System) related traps.
           "
    DEFVAL {disable}
       ::= { bsnTrapControl 11 }

bsnRADIUSServerNotResponding    NOTIFICATION-TYPE
    STATUS current
    DESCRIPTION
    "This trap is to indicate that no RADIUS server(s) are responding
    to authentication requests sent by the RADIUS client within the
    MWAR device(Switch)."
    ::= { bsnTraps 26 }

bsnAuthenticationFailure    NOTIFICATION-TYPE
    OBJECTS { bsnAuthFailureUserType, bsnAuthFailureUserName}
    STATUS current
    DESCRIPTION
    "This trap is to inform that client authentication failure has
     occured at MWAR(Switch). This could be cli/web user, wlan user, 
     or Mac Authorized user. ServiceType will indicate which type of 
     user it is and userName will be cli/web/wlan userName or 
     MacAddress of Mac Authorized User"
    ::= { bsnTraps 27 }


-- IPSEC Traps

bsnRemoteIPv4Address OBJECT-TYPE
    SYNTAX  IpAddress
    MAX-ACCESS  accessible-for-notify
    STATUS  current
    DESCRIPTION
            ""
    ::= { bsnTrapVariable 3 }

bsnIpsecErrorCount OBJECT-TYPE
    SYNTAX  Integer32
    MAX-ACCESS  accessible-for-notify
    STATUS  current
    DESCRIPTION
            ""
    ::= { bsnTrapVariable 4 }

bsnIpsecSPI OBJECT-TYPE
    SYNTAX  Integer32
    MAX-ACCESS  accessible-for-notify
    STATUS  current
    DESCRIPTION
            ""
    ::= { bsnTrapVariable 5 }

bsnRemoteUdpPort OBJECT-TYPE
    SYNTAX  Integer32 (0..65535)
    MAX-ACCESS  accessible-for-notify
    STATUS  current
    DESCRIPTION
            ""
    ::= { bsnTrapVariable 6 }

bsnIkeAuthMethod OBJECT-TYPE
    SYNTAX  Integer32
    MAX-ACCESS  accessible-for-notify
    STATUS  current
    DESCRIPTION
            ""
    ::= { bsnTrapVariable 7 }

bsnIkeTotalInitFailures OBJECT-TYPE
    SYNTAX  Integer32
    MAX-ACCESS  accessible-for-notify
    STATUS  current
    DESCRIPTION
            ""
    ::= { bsnTrapVariable 8 }

bsnIkeTotalInitNoResponses OBJECT-TYPE
    SYNTAX  Integer32
    MAX-ACCESS  accessible-for-notify
    STATUS  current
    DESCRIPTION
            ""
    ::= { bsnTrapVariable 9 }

bsnIkeTotalRespFailures OBJECT-TYPE
    SYNTAX  Integer32
    MAX-ACCESS  accessible-for-notify
    STATUS  current
    DESCRIPTION
            ""
    ::= { bsnTrapVariable 10 }

bsnNotifiesSent OBJECT-TYPE
    SYNTAX  Integer32
    MAX-ACCESS  accessible-for-notify
    STATUS  current
    DESCRIPTION
            ""
    ::= { bsnTrapVariable 11 }

bsnNotifiesReceived OBJECT-TYPE
    SYNTAX  Integer32
    MAX-ACCESS  accessible-for-notify
    STATUS  current
    DESCRIPTION
            ""
    ::= { bsnTrapVariable 12 }

bsnSuiteInitFailures OBJECT-TYPE
    SYNTAX  Integer32
    MAX-ACCESS  accessible-for-notify
    STATUS  current
    DESCRIPTION
            ""
    ::= { bsnTrapVariable 13 }

bsnSuiteRespondFailures OBJECT-TYPE
    SYNTAX  Integer32
    MAX-ACCESS  accessible-for-notify
    STATUS  current
    DESCRIPTION
            ""
    ::= { bsnTrapVariable 14 }

bsnInitiatorCookie OBJECT-TYPE
    SYNTAX      OCTET STRING (SIZE (8))
    MAX-ACCESS  accessible-for-notify
    STATUS      current
    DESCRIPTION
       "The initiator cookie used in an ISAKMP message, to be
        associated with a trap."
   ::= { bsnTrapVariable 15 }

bsnResponderCookie OBJECT-TYPE
   SYNTAX      OCTET STRING (SIZE (8))
   MAX-ACCESS  accessible-for-notify
   STATUS      current
   DESCRIPTION
      "The responder cookie used in an ISAKMP message, to be
      associated with a trap."
   ::= { bsnTrapVariable 16 }

bsnIsakmpInvalidCookies OBJECT-TYPE
    SYNTAX  Integer32
    MAX-ACCESS  accessible-for-notify
    STATUS  current
    DESCRIPTION
            ""
    ::= { bsnTrapVariable 17 }

bsnIpsecTrapsMask OBJECT-TYPE
        SYNTAX   Unsigned32
        MAX-ACCESS   read-write
        STATUS   current
        DESCRIPTION
           "This mask describes what events merit traps to network 
            management.  If the bit for a particular event is turned 
            on then notification will be generated on event occurance.
                Event                    corresponding bit
                -----                    -----------------
                bsnIpsecEspAuthFailureTrap          1
                bsnIpsecEspReplayFailureTrap        2
                bsnIpsecEspPolicyFailureTrap        4
                bsnIpsecEspInvalidSpiTrap           8
                bsnIpsecOtherPolicyFailureTrap     16
                bsnIpsecIkeNegFailure              32
                bsnIpsecSuiteNegFailure            64   
                bsnIpsecInvalidCookieTrap         128
           "
       ::= { bsnTrapControl 5 }


 bsnIpsecEspAuthFailureTrap NOTIFICATION-TYPE
        OBJECTS {
            bsnRemoteIPv4Address,
            bsnIpsecErrorCount
        }
        STATUS      current
        DESCRIPTION
            "IPsec packets with invalid hashes were found in an inbound
            ESP SA. The total number of authentication errors
            accumulated is sent for the specific row of the
            ipsecSaEspInTable table for the SA; this provides the
            identity of the SA in which the error occurred.

            Implementations SHOULD send one trap per SA (within a
            reasonable time period), rather than sending one trap per
            packet."
        ::= { bsnTraps 28 }

 bsnIpsecEspReplayFailureTrap NOTIFICATION-TYPE
        OBJECTS {
        bsnRemoteIPv4Address,
            bsnIpsecErrorCount
        }
        STATUS      current
        DESCRIPTION
            "IPsec packets with invalid sequence numbers were found in
            an inbound ESP SA. The total number of replay errors
            accumulated is sent for the specific row of the
            ipsecSaEspInTable table for the SA; this provides the
            identity of the SA in which the error occurred.

            Implementations SHOULD send one trap per SA (within a
            reasonable time period), rather than sending one trap per
            packet."
        ::= { bsnTraps 29 }

 bsnIpsecEspInvalidSpiTrap NOTIFICATION-TYPE
        OBJECTS {
        bsnRemoteIPv4Address,
            bsnIpsecSPI
        }
        STATUS      current
        DESCRIPTION
            "A packet with an unknown SPI was detected from the
            specified peer with the specified SPI using the specified
            protocol. The destination address of the received packet is
            specified by ipsecLocalAddress.

            The value ifIndex may be 0 if this optional linkage is
            unsupported.

            If the object ipsecSecurityProtocol has the value for
            IPcomp, then the ipsecSPI object is the CPI of the packet.

            Implementations SHOULD send one trap per peer (within a
            reasonable time period), rather than sending one trap per
            packet."
        ::= { bsnTraps 31 }

 bsnIpsecIkeNegFailure NOTIFICATION-TYPE
     OBJECTS   {
            bsnRemoteIPv4Address,
            bsnRemoteUdpPort,
            bsnIkeAuthMethod,
            bsnIkeTotalInitFailures,
            bsnIkeTotalInitNoResponses,
            bsnIkeTotalRespFailures,
            bsnNotifiesSent,
            bsnNotifiesReceived
        }
        STATUS  current
        DESCRIPTION
            "An attempt to negotiate a phase 1 IKE SA failed.
            The notification counts are also sent as part of the trap,
            along with the current value of the total negotiation error
            counters for ISAKMP."
        ::= { bsnTraps 33 }

 bsnIpsecSuiteNegFailure NOTIFICATION-TYPE
     OBJECTS   {
            bsnRemoteIPv4Address,
            bsnSuiteInitFailures,
            bsnSuiteRespondFailures,
            bsnNotifiesSent,
            bsnNotifiesReceived
        }
        STATUS  current
        DESCRIPTION
            "An attempt to negotiate a phase 2 SA suite for the
            specified selector failed.
            The current total failure counts are passed as well as the
            notification type counts for the notify involved in the
            failure."
        ::= { bsnTraps 34 }

 bsnIpsecInvalidCookieTrap NOTIFICATION-TYPE
        OBJECTS {
            bsnRemoteIPv4Address,
            bsnRemoteUdpPort,
            bsnInitiatorCookie,
            bsnResponderCookie,
            bsnIsakmpInvalidCookies
        }
        STATUS  current
        DESCRIPTION
            "ISAKMP packets with invalid cookies were detected from the
            specified source, intended for the specified destination.

            The initiator and responder cookies are also sent with the
            trap.

            The current count is sent to allow the trap to accurately
            relfect dropped and throttled traps.

            Implementations SHOULD send one trap per peer (within a
            reasonable time period, rather than sending one trap per
            packet."
        ::= { bsnTraps 35}

bsnRogueAPTrapEnable OBJECT-TYPE
        SYNTAX   INTEGER {disable(0),enable(1)}
        MAX-ACCESS   read-write
        STATUS   current
        DESCRIPTION
           "If Rogue AP Detection and Removed Traps need to be sent "
       ::= { bsnTrapControl 6 }


bsnRogueAPDetected NOTIFICATION-TYPE
    OBJECTS { bsnRogueAPDot11MacAddress,
              bsnRogueAPAirespaceAPMacAddress,
              bsnRogueAPAirespaceAPSlotId,
              bsnRogueAPSsid,bsnRogueAPChannelNumber,
              bsnRogueAPAirespaceAPRSSI,
              bsnRogueAPAirespaceAPSNR, 
              bsnRogueAPOnWiredNetwork,
              bsnRogueAdhocMode, 
              bsnRogueAPRadioType, 
              bsnRogueAPAirespaceAPName}
    STATUS current
    DESCRIPTION
        "When a Rogue AP is detected this Trap will be sent out along
         with APMacAddress on which its detected"
    ::= { bsnTraps 36 }

bsnRogueAPRemoved NOTIFICATION-TYPE
    OBJECTS { bsnRogueAPDot11MacAddress,
              bsnRogueAPAirespaceAPMacAddress,
              bsnRogueAPAirespaceAPSlotId,
              bsnRogueAPRadioType, 
              bsnRogueAPAirespaceAPName }
    STATUS current
    DESCRIPTION
        "When a Rogue AP that was detected earlier no longer exists
         this Trap will be sent out along
         with APMacAddress on which its detected"
    ::= { bsnTraps 41 }

bsnRogueAPDetectedOnWiredNetwork NOTIFICATION-TYPE
    OBJECTS { bsnRogueAPDot11MacAddress,bsnRogueAPOnWiredNetwork}
    STATUS current
    DESCRIPTION
        "When a Rogue is detected on the wired network this trap will 
         be sent out.
         The same trap with bsnRogueAPOnWiredNetwork set to no will 
         clear the previous trap."
    ::= { bsnTraps 59 }

bsnApHasNoRadioCards NOTIFICATION-TYPE
    OBJECTS { bsnAPMacAddrTrapVariable }
    STATUS current
    DESCRIPTION
        "When an AP has no radio cards present on it, the switch 
         sends this trap."
    ::= { bsnTraps 60 }

bsnDuplicateIpAddressReported NOTIFICATION-TYPE
    OBJECTS { bsnDuplicateIpReportedByAP, 
              bsnAPMacAddrTrapVariable, 
              bsnDuplicateIpTrapVariable, 
              bsnRogueAPDot11MacAddress, 
              bsnDuplicateIpTrapClear}
    STATUS current
    DESCRIPTION
        "This trap is issued when the switch or an AP detects another 
         machine using its IP Address. The first variable has value 
         yes if the duplicate IP is reported by an AP. In that case, 
         the second attribute will carry the AP MAC Address. The third
         variable is the duplicate IP address in question and the last 
         attribute is the MAC Address of the machine that is found to
         be using the duplicate IP."
    ::= { bsnTraps 61 }


bsnAPContainedAsARogue NOTIFICATION-TYPE
    OBJECTS { bsnAPDot3MacAddress, bsnAPIfSlotId, 
              bsnAPIfType, bsnClearTrapVariable }
    STATUS current
    DESCRIPTION
        "When our AP detects that it is being contained by another AP,
         this trap is issued. The clear flag is true if the AP is no 
         longer being contained."
    ::= { bsnTraps 62 }

bsnNetworkStateChanged NOTIFICATION-TYPE
    OBJECTS { bsnNetworkType, bsnNetworkState}
    STATUS current
    DESCRIPTION
        "When the 802.11a or b/g network state is changed this trap 
         is issued."
    ::= { bsnTraps 69 }

bsnSignatureAttackDetected NOTIFICATION-TYPE
    OBJECTS { bsnAPDot3MacAddress, bsnAPIfSlotId, 
              bsnAPName, bsnAPIfType, bsnSignatureType, 
              bsnSignatureName, bsnSignatureDescription, 
              bsnClearTrapVariable, bsnSignatureAttackPreced, 
              bsnSignatureAttackFrequency, 
              bsnSignatureAttackChannel, 
              bsnSignatureAttackerMacAddress,
              bsnSignatureMacInfo }
    STATUS current
    DESCRIPTION
        "This trap is sent out when a signature attack is detected by 
         the switch. The standard and custom signatures are predefined
         on the switch (see bsnSignatureConfig group). The signatures 
         also defines if its detection should be reported. The trap 
         variables bsnSignatureName and bsnSignatureDescription are 
         retrieved from the detected signature definition. Clear Trap 
         Variable is turned on when the signature attack stops. The 
         signature's quiet time configuration speicifes the time after
         which the clear trap would be sent. bsnSignatureMacInfo 
         indicates whether the signature is used to track 
         pattern matches for all source MAC addresses together or 
         seperately for individual source MAC addresses.  
         bsnSignatureAttackFrequency will carry the value for a 
         specific MAC address or for all MAC addresses depending on 
         bsnSignatureMacInfo. "
    ::= { bsnTraps 70 }

bsnAPRadioCardTxFailure NOTIFICATION-TYPE
    OBJECTS { bsnAPDot3MacAddress, bsnAPIfSlotId, bsnAPIfType}
    STATUS current
    DESCRIPTION
        "This trap is sent by the switch when a radio card on an AP 
         stops transmitting."
    ::= { bsnTraps 71 }

bsnAPRadioCardTxFailureClear NOTIFICATION-TYPE
    OBJECTS { bsnAPDot3MacAddress, bsnAPIfSlotId, bsnAPIfType}
    STATUS current
    DESCRIPTION
        "This trap is sent by the switch when a radio card on an AP 
         starts transmitting again after a prior failure."
    ::= { bsnTraps 72 }

bsnAPRadioCardRxFailure NOTIFICATION-TYPE
    OBJECTS { bsnAPDot3MacAddress, bsnAPIfSlotId, bsnAPIfType}
    STATUS current
    DESCRIPTION
        "This trap is sent by the switch when a radio card on an AP 
         stops receiving."
    ::= { bsnTraps 73 }

bsnAPRadioCardRxFailureClear NOTIFICATION-TYPE
    OBJECTS { bsnAPDot3MacAddress, bsnAPIfSlotId, bsnAPIfType}
    STATUS current
    DESCRIPTION
        "This trap is sent by the switch when a radio card on an AP 
         starts receiving again after a prior failure."
    ::= { bsnTraps 74 }

bsnAPImpersonationDetected NOTIFICATION-TYPE
    OBJECTS { bsnImpersonatedAPMacAddr, bsnAPDot3MacAddress, 
              bsnAPIfSlotId, bsnAPIfType}
    STATUS current
    DESCRIPTION
        "This trap is sent by the switch when a radio of an 
         authenticated AP hears from another AP whose MAC Address
         neither matches that of a rogue's and nor is it an 
         authenticated neighbor of the detecting AP."
    ::= { bsnTraps 75 }
    
bsnAPRegulatoryDomainMismatch NOTIFICATION-TYPE
    OBJECTS { bsnAPDot3MacAddress, bsnAPName, 
              bsnApRegulatoryDomain, bsnGlobalDot11CountryIndex}
    STATUS current
    DESCRIPTION
        "This trap is generated if an AP's regulatory domain doesn't 
         match the country the switch is configured for.  Due to the 
         mismatch, the AP will fail to associate with the Switch."
    ::= { bsnTraps 79 }

bsnTrustedApHasInvalidPreamble NOTIFICATION-TYPE
    OBJECTS { bsnRogueAPDot11MacAddress, bsnTrustedApPreambleUsed, 
              bsnTrustedApPreambleRequired, bsnClearTrapVariable}
    STATUS current
    DESCRIPTION
    "Issued when a Trusted Rogue AP is auto contained for using invalid
     preamble. The second param is for the preamble used and the third
     param is for preamble required. If the clear variable has value 
     true, then the trap clears the earlier alert."
    ::= { bsnTraps 76 }

bsnCurrentRadiosCount OBJECT-TYPE
    SYNTAX  Integer32
    MAX-ACCESS  accessible-for-notify
    STATUS  current
    DESCRIPTION
            ""
    ::= { bsnTrapVariable 18 }

bsnLicenseRadioCount OBJECT-TYPE
    SYNTAX  Integer32
    MAX-ACCESS  accessible-for-notify
    STATUS  current
    DESCRIPTION
            ""
    ::= { bsnTrapVariable 19 }

bsnMaxRogueCount OBJECT-TYPE
    SYNTAX  Integer32
    MAX-ACCESS  accessible-for-notify
    STATUS  current
    DESCRIPTION
            ""
    ::= { bsnTrapVariable 33 }

bsnStationMacAddress OBJECT-TYPE
    SYNTAX MacAddress
    MAX-ACCESS  accessible-for-notify
    STATUS  current
    DESCRIPTION
            ""
    ::= { bsnTrapVariable 34 }

bsnStationAPMacAddr OBJECT-TYPE
    SYNTAX MacAddress
    MAX-ACCESS  accessible-for-notify
    STATUS  current
    DESCRIPTION
            ""
    ::= { bsnTrapVariable 35 }

bsnStationAPIfSlotId OBJECT-TYPE
    SYNTAX INTEGER(0..15)
    MAX-ACCESS  accessible-for-notify
    STATUS  current
    DESCRIPTION
            ""
    ::= { bsnTrapVariable 36 }


bsnStationReasonCode OBJECT-TYPE
    SYNTAX INTEGER { unspecified (1),
        previousAuthNotValid (2),
        deauthenticationLeaving (3),
        disassociationDueToInactivity (4),
        disassociationAPBusy (5),
        class2FrameFromNonAuthStation (6),
        class2FrameFromNonAssStation (7),
        disassociationStaHasLeft (8),
        staReqAssociationWithoutAuth (9),
        missingReasonCode (99)
    }
    MAX-ACCESS  accessible-for-notify
    STATUS  current
    DESCRIPTION
            ""
    ::= { bsnTrapVariable 37 }

bsnStationBlacklistingReasonCode OBJECT-TYPE
    SYNTAX INTEGER { failed80211Auth (1),
        failedAssociation (2),
        ipTheft (3),
        failed8021xAuth (4),
        failedWebAuth (5)
    }
    MAX-ACCESS  accessible-for-notify
    STATUS  current
    DESCRIPTION
            ""
    ::= { bsnTrapVariable 38 }

bsnStationUserName OBJECT-TYPE
    SYNTAX  DisplayString
    MAX-ACCESS  accessible-for-notify
    STATUS  current
    DESCRIPTION
            "The user name of a client. This is used for the Client 
             Associated trap. It may be null when not known."
    ::= { bsnTrapVariable 39 }

bsnRogueAPOnWiredNetwork OBJECT-TYPE
    SYNTAX   INTEGER {no(0),yes(1)}
    MAX-ACCESS  accessible-for-notify
    STATUS  current
    DESCRIPTION
            "This is the flag used on the bsnRogueAPDetected trap to 
             state if the rogue is found on the wired network.
             Typically, after a rogue is found, there may be another 
             bsnRogueAPDetected trap that will have the value
             of this flag 1 if the rogue is detected on the wired 
             network."
    ::= { bsnTrapVariable 40 }

bsnNavDosAttackSourceMacAddr OBJECT-TYPE
    SYNTAX MacAddress
    MAX-ACCESS  accessible-for-notify
    STATUS  current
    DESCRIPTION
            "MAC address generating the attack."
    ::= { bsnTrapVariable 41 }

bsnWlanIdTrapVariable OBJECT-TYPE
    SYNTAX INTEGER(1..17)
    MAX-ACCESS  accessible-for-notify
    STATUS  current
    DESCRIPTION
            "WLAN ID used by the client when the WPA MIC error 
             counter measure was activated."
    ::= { bsnTrapVariable 42 }

bsnUserIpAddress OBJECT-TYPE
    SYNTAX IpAddress
    MAX-ACCESS  accessible-for-notify
    STATUS  current
    DESCRIPTION
            ""
    ::= { bsnTrapVariable 43 }

bsnRogueAdhocMode OBJECT-TYPE
    SYNTAX   INTEGER {no(0),yes(1)}
    MAX-ACCESS  accessible-for-notify
    STATUS  current
    DESCRIPTION
           "This is the flag used on the bsnRogueAPDetected trap to 
            state if the rogue found is an Adhoc rogue or it is an AP."
    ::= { bsnTrapVariable 44 }

bsnClearTrapVariable OBJECT-TYPE
    SYNTAX   INTEGER {false(0),true(1)}
    MAX-ACCESS  accessible-for-notify
    STATUS  current
    DESCRIPTION
            "This is the flag is used to indicate if this is a clear 
             trap for the original alert or not."
    ::= { bsnTrapVariable 45 }

bsnDuplicateIpTrapVariable OBJECT-TYPE
    SYNTAX   IpAddress
    MAX-ACCESS  accessible-for-notify
    STATUS  current
    DESCRIPTION
            "This field is used on the bsnDuplicateIpAddressReported 
             trap to contain the IP Address in question when switch 
             or an AP detected a duplicate IP Address on another 
             machine."
    ::= { bsnTrapVariable 46 }

bsnDuplicateIpTrapClear OBJECT-TYPE
    SYNTAX   INTEGER {false(0),true(1)}
    MAX-ACCESS  accessible-for-notify
    STATUS  current
    DESCRIPTION
            "This is the flag used to indicate clear state for the 
             bsnDuplicateIpAddressReported trap."
    ::= { bsnTrapVariable 47 }

bsnDuplicateIpReportedByAP OBJECT-TYPE
    SYNTAX   INTEGER {no(0),yes(1)}
    MAX-ACCESS  accessible-for-notify
    STATUS  current
    DESCRIPTION
            "This is the flag used on the bsnDuplicateIpAddressReported
             trap to indicate whether the switch or an AP detected a 
             duplicate IP Address on another machine."
    ::= { bsnTrapVariable 48 }

bsnTrustedApRadioPolicyRequired OBJECT-TYPE
    SYNTAX   INTEGER{none(0), dot11b(1), dot11a(2), dot11bg(3)}
    MAX-ACCESS  accessible-for-notify
    STATUS  current
    DESCRIPTION
            "This is the radio policy required by a trusted Rogue."
    ::= { bsnTrapVariable 49 }

bsnTrustedApEncryptionUsed OBJECT-TYPE
    SYNTAX   INTEGER {none(0), open(1), wep(2), wpa(3)}
    MAX-ACCESS  accessible-for-notify
    STATUS  current
    DESCRIPTION
            "This is the encryption type used by a trusted Rogue."
    ::= { bsnTrapVariable 50 }

bsnTrustedApEncryptionRequired OBJECT-TYPE
    SYNTAX   INTEGER {none(0), open(1), wep(2), wpa(3)}
    MAX-ACCESS  accessible-for-notify
    STATUS  current
    DESCRIPTION
            "This is the encryption type required by a trusted Rogue."
    ::= { bsnTrapVariable 51 }

bsnTrustedApRadioPolicyUsed OBJECT-TYPE
    SYNTAX   INTEGER {none(0), dot11b(1), dot11a(2), dot11bg(3)}
    MAX-ACCESS  accessible-for-notify
    STATUS  current
    DESCRIPTION
            "This is the radio policy used by a trusted Rogue."
    ::= { bsnTrapVariable 52 }

bsnNetworkType OBJECT-TYPE
    SYNTAX  INTEGER {dot11b(1),dot11a(2)}
    MAX-ACCESS  accessible-for-notify
    STATUS  current
    DESCRIPTION
            ""
    ::= { bsnTrapVariable 53 }

bsnNetworkState OBJECT-TYPE
    SYNTAX  INTEGER {disable(0),enable(1)}
    MAX-ACCESS  accessible-for-notify
    STATUS  current
    DESCRIPTION
            ""
    ::= { bsnTrapVariable 54 }

bsnSignatureType OBJECT-TYPE
    SYNTAX  INTEGER {standard(0),custom(1)}
    MAX-ACCESS  accessible-for-notify
    STATUS  current
    DESCRIPTION
            "Type of Signature whose attack is detected by the switch."
    ::= { bsnTrapVariable 55 }

bsnSignatureName OBJECT-TYPE
    SYNTAX DisplayString (SIZE(0..20))
    MAX-ACCESS  accessible-for-notify
    STATUS  current
    DESCRIPTION
            "Name of the Signature whose attack is detected by the 
             switch."
    ::= { bsnTrapVariable 56 }

bsnSignatureDescription OBJECT-TYPE
    SYNTAX DisplayString (SIZE(0..100))
    MAX-ACCESS  accessible-for-notify
    STATUS  current
    DESCRIPTION
            "Description of the Signature whose attack is detected by 
             the switch."
    ::= { bsnTrapVariable 57 }

bsnImpersonatedAPMacAddr OBJECT-TYPE
    SYNTAX MacAddress
    MAX-ACCESS  accessible-for-notify
    STATUS  current
    DESCRIPTION
            "MAC Address of the AP impersonated by another AP."
    ::= { bsnTrapVariable 58 }

bsnTrustedApPreambleUsed OBJECT-TYPE
        SYNTAX INTEGER { none(0), short(1), long(2)}
        MAX-ACCESS  accessible-for-notify
        STATUS current
        DESCRIPTION
                "The Preamble on this detecting AP."
    ::= { bsnTrapVariable 59 }

bsnTrustedApPreambleRequired OBJECT-TYPE
        SYNTAX INTEGER { none(0), short(1), long(2)}
        MAX-ACCESS  accessible-for-notify
        STATUS current
        DESCRIPTION
                "The Preamble on this detecting AP."
    ::= { bsnTrapVariable 60 }

bsnSignatureAttackPreced OBJECT-TYPE
    SYNTAX INTEGER(0..65535)
    MAX-ACCESS accessible-for-notify
    STATUS current
    DESCRIPTION
        "The preced in the standard/custom signature list."
    ::= { bsnTrapVariable 61 }

bsnSignatureAttackFrequency OBJECT-TYPE
    SYNTAX INTEGER(0..65535)
    MAX-ACCESS accessible-for-notify
    STATUS current
    DESCRIPTION
        "The preced in the standard/custom signature list."
    ::= { bsnTrapVariable 62 }

bsnSignatureAttackChannel OBJECT-TYPE
    SYNTAX INTEGER(0..65535)
    MAX-ACCESS accessible-for-notify
    STATUS current
    DESCRIPTION
        "The preced in the standard/custom signature list."
    ::= { bsnTrapVariable 63 }

bsnSignatureAttackerMacAddress OBJECT-TYPE
    SYNTAX MacAddress
    MAX-ACCESS accessible-for-notify
    STATUS current
    DESCRIPTION
        "The MAC address of the Attacker's mac-interface."
    ::= { bsnTrapVariable 64 }

bsnApRegulatoryDomain OBJECT-TYPE
        SYNTAX INTEGER { a(0), e(1), 
                        i(6), j(9), 
                        c(16), n(21), 
                        k(32), p(33), 
                        s(34), t(35), r(48),
                        notavailable(65535)}
        MAX-ACCESS  accessible-for-notify
        STATUS current
        DESCRIPTION
                "The regulatory domain configured on an AP."
    ::= { bsnTrapVariable 68 }

bsnRadiosExceedLicenseCount NOTIFICATION-TYPE
    OBJECTS { bsnCurrentRadiosCount,bsnLicenseRadioCount }
    STATUS current
    DESCRIPTION
    "Whenever the currently associated Radios exceed the License Count
     This trap will be sent to annoy the Customer"
    ::= { bsnTraps 42 }

bsnSensedTemperatureTooHigh NOTIFICATION-TYPE
    OBJECTS { bsnSensorTemperature }
    STATUS current
    DESCRIPTION
    "Temperature sensor temp too High - temp is too high on the unit.  
     Immediate action should be taken"
    ::= { bsnTraps 43 }

bsnSensedTemperatureTooLow NOTIFICATION-TYPE
    OBJECTS { bsnSensorTemperature }
    STATUS current
    DESCRIPTION
    "Temperature sensor temp too Low  - temp is too high on the unit. 
     Immediate action should be taken"
    ::= { bsnTraps 44 }

bsnTemperatureSensorFailure NOTIFICATION-TYPE
    STATUS current
    DESCRIPTION
    "Temperature sensor hw failure - temp sensor has failed.  
     Temperature is unknown"
    ::= { bsnTraps 45 }

bsnTemperatureSensorClear NOTIFICATION-TYPE
    OBJECTS { bsnSensorTemperature }
    STATUS current
    DESCRIPTION
    "Temperature sensor clear -- temp sensor alarm condition is over.  
     sensor is operating within proper temp range"
    ::= { bsnTraps 46 }

bsnPOEControllerFailure NOTIFICATION-TYPE
    STATUS current
    DESCRIPTION
    "POE Controller has failed. Its a very critical trap.
     User intervention is required."
    ::= { bsnTraps 47 }

bsnMaxRogueCountExceeded NOTIFICATION-TYPE
    OBJECTS { bsnMaxRogueCount }
    STATUS current
    DESCRIPTION
    "The number of rogues has exceeded the maximum Rogues allowed"
    ::= { bsnTraps 48 }

bsnMaxRogueCountClear NOTIFICATION-TYPE
    OBJECTS { bsnMaxRogueCount }
    STATUS current
    DESCRIPTION
    "The number of rogues is within the maximum Rogues allowed"
    ::= { bsnTraps 49 }

bsnApMaxRogueCountExceeded NOTIFICATION-TYPE
    OBJECTS { bsnAPMacAddrTrapVariable, bsnMaxRogueCount }
    STATUS current
    DESCRIPTION
    "The number of rogues has exceeded the maximum Rogues allowed on 
     the AP"
    ::= { bsnTraps 50 }

bsnApMaxRogueCountClear NOTIFICATION-TYPE
    OBJECTS { bsnAPMacAddrTrapVariable, bsnMaxRogueCount }
    STATUS current
    DESCRIPTION
    "The number of rogues is within the maximum Rogues allowed on the 
     AP"
    ::= { bsnTraps 51 }

bsnApBigNavDosAttack NOTIFICATION-TYPE
    OBJECTS { bsnAPMacAddrTrapVariable, 
              bsnAPSlotIdTrapVariable, 
              bsnNavDosAttackSourceMacAddr}
    STATUS current
    DESCRIPTION
    "The AP sent a string of messages with large NAV field and all 
     802.11 traffic on that channel was suspended."
    ::= { bsnTraps 55 }

bsnTooManyUnsuccessLoginAttempts NOTIFICATION-TYPE
    OBJECTS { bsnUserIpAddress, bsnStationUserName }
    STATUS current
    DESCRIPTION
    "The Management User made too many unsuccessful login attempts."
    ::= { bsnTraps 56 }

bsnWepKeyDecryptError NOTIFICATION-TYPE
    OBJECTS { bsnStationMacAddress, 
              bsnStationAPMacAddr, 
              bsnStationAPIfSlotId}
    STATUS current
    DESCRIPTION
    "Issued when a decrypt error occurrs. The WEP Key configured at 
     the station may be wrong."
    ::= { bsnTraps 57 }

bsnWpaMicErrorCounterActivated NOTIFICATION-TYPE
    OBJECTS { bsnStationMacAddress, 
              bsnStationAPMacAddr, 
              bsnStationAPIfSlotId, 
              bsnWlanIdTrapVariable}
    STATUS current
    DESCRIPTION
    "Issued when a WPA MIC error occurs and a counter measure is 
     activated at the AP."
    ::= { bsnTraps 58 }

bsnAdhocRogueAutoContained NOTIFICATION-TYPE
    OBJECTS { bsnRogueAPDot11MacAddress, bsnClearTrapVariable}
    STATUS current
    DESCRIPTION
    "Issued when an Adhoc Rogue is auto contained.
     If the clear variable has value true, then the trap clears the 
     earlier alert."
    ::= { bsnTraps 65 }

bsnRogueApAutoContained NOTIFICATION-TYPE
    OBJECTS { bsnRogueAPDot11MacAddress, bsnClearTrapVariable}
    STATUS current
    DESCRIPTION
    "Issued when a Rogue AP is auto contained for advertising our SSID.
     If the clear variable has value true, then the trap clears the 
     earlier alert."
    ::= { bsnTraps 66 }

bsnTrustedApHasInvalidEncryption NOTIFICATION-TYPE
    OBJECTS { bsnRogueAPDot11MacAddress, 
              bsnTrustedApEncryptionUsed, 
              bsnTrustedApEncryptionRequired, 
              bsnClearTrapVariable}
    STATUS current
    DESCRIPTION
    "Issued when a Trusted Rogue AP is auto contained for using 
     invalid encryption. The second param is for the encryption used 
     and the third param is for encryption required.
     If the clear variable has value true, then the trap clears the 
     earlier alert."
    ::= { bsnTraps 67 }

bsnTrustedApHasInvalidRadioPolicy NOTIFICATION-TYPE
    OBJECTS { bsnRogueAPDot11MacAddress, 
              bsnTrustedApRadioPolicyUsed, 
              bsnTrustedApRadioPolicyRequired, 
              bsnClearTrapVariable}
    STATUS current
    DESCRIPTION
    "Issued when a Trusted Rogue AP is auto contained for using 
     invalid radio policy.  The second param is for the radio policy 
     used and the third param is for radio policy required.
     If the clear variable has value true, then the trap clears the 
     earlier alert."
    ::= { bsnTraps 68 }

bsnTrustedApHasInvalidSsid NOTIFICATION-TYPE
    OBJECTS { bsnRogueAPDot11MacAddress, bsnClearTrapVariable}
    STATUS current
    DESCRIPTION
    "Issued when a Trusted Rogue AP is auto contained for advertising 
     invalid SSID.
     If the clear variable has value true, then the trap clears the 
     earlier alert."
    ::= { bsnTraps 63 }

bsnTrustedApIsMissing NOTIFICATION-TYPE
    OBJECTS { bsnRogueAPDot11MacAddress, bsnClearTrapVariable}
    STATUS current
    DESCRIPTION
    "Issued when a Trusted Rogue AP is missing or has failed.
     If the clear variable has value true, then the trap clears the 
     earlier alert."
    ::= { bsnTraps 64 }

-- ********************************************************************
-- * Begin of Syslog
-- ********************************************************************
bsnSyslog OBJECT IDENTIFIER ::= { bsnUtility 1 }

bsnSyslogEnable  OBJECT-TYPE
        SYNTAX   INTEGER {no(0),yes(1)}
        MAX-ACCESS   read-write
        STATUS   current
        DESCRIPTION
        ""
       ::= { bsnSyslog 1 }

bsnSyslogRemoteAddress  OBJECT-TYPE
        SYNTAX   DisplayString
        MAX-ACCESS   read-write
        STATUS   current
        DESCRIPTION
        "This would be the IP Address or host name"
       ::= { bsnSyslog 2 }

-- ********************************************************************
-- bsn Ping
-- ********************************************************************
bsnPing OBJECT IDENTIFIER ::= { bsnUtility 2 }

bsnPingTestTable OBJECT-TYPE
    SYNTAX SEQUENCE OF BsnPingTestEntry
    MAX-ACCESS not-accessible
    STATUS current
    DESCRIPTION
    " PingTest Table"
    ::= { bsnPing 1 }

bsnPingTestEntry OBJECT-TYPE
    SYNTAX BsnPingTestEntry
    MAX-ACCESS not-accessible
    STATUS current
    DESCRIPTION
        "An Entry (conceptual row) in the bsnPingTest
        Table."
    INDEX { bsnPingTestId }
    ::= { bsnPingTestTable  1 }

BsnPingTestEntry ::=
        SEQUENCE {      bsnPingTestId            Integer32,
                        bsnPingTestIPAddress     IpAddress,
                        bsnPingTestSendCount     Integer32,
                        bsnPingTestReceivedCount Integer32,
                        bsnPingTestStatus        INTEGER,
                        bsnPingTestRowStatus     RowStatus}

bsnPingTestId OBJECT-TYPE
    SYNTAX Integer32 (0..24)
    MAX-ACCESS read-create
    STATUS current
    DESCRIPTION
        "Test ID"
    ::= { bsnPingTestEntry 1 }

bsnPingTestIPAddress OBJECT-TYPE
    SYNTAX IpAddress
    MAX-ACCESS read-create
    STATUS current
    DESCRIPTION
        "Ip Address to ping"
    ::= { bsnPingTestEntry 2 }

bsnPingTestSendCount OBJECT-TYPE
    SYNTAX Integer32 (1..20)
    MAX-ACCESS read-create
    STATUS current
    DESCRIPTION
        "Number of bytes sent"
    ::= { bsnPingTestEntry 3 }

bsnPingTestReceivedCount OBJECT-TYPE
    SYNTAX Integer32 (1..20)
    MAX-ACCESS read-only
    STATUS current
    DESCRIPTION
        "Number of bytes received."
    ::= { bsnPingTestEntry 4 }

bsnPingTestStatus OBJECT-TYPE
    SYNTAX INTEGER { inprogress(1),complete(2) }
    MAX-ACCESS read-only
    STATUS current
    DESCRIPTION
        "Status of the ping test"
    ::= { bsnPingTestEntry 5 }

bsnPingTestRowStatus OBJECT-TYPE
    SYNTAX RowStatus
    MAX-ACCESS read-create
    STATUS current
    DESCRIPTION
        "Row Status"
    ::= { bsnPingTestEntry 25 }

-- ********************************************************************
-- bsn Link
-- ********************************************************************
bsnLinkTest OBJECT IDENTIFIER ::= { bsnUtility 3 }

bsnLinkTestTable OBJECT-TYPE
    SYNTAX SEQUENCE OF BsnLinkTestEntry
    MAX-ACCESS not-accessible
    STATUS deprecated
    DESCRIPTION
    " LinkTest Table"
    ::= { bsnLinkTest 1 }

bsnLinkTestEntry OBJECT-TYPE
    SYNTAX BsnLinkTestEntry
    MAX-ACCESS not-accessible
    STATUS deprecated
    DESCRIPTION
        "An Entry (conceptual row) in the bsnLinkTest
        Table."
    INDEX { bsnLinkTestId }
    ::= { bsnLinkTestTable  1 }

BsnLinkTestEntry ::=
        SEQUENCE {      bsnLinkTestId               Integer32,
                        bsnLinkTestMacAddress       MacAddress,
                        bsnLinkTestSendPktCount     Integer32,
                        bsnLinkTestSendPktLength    Integer32,
                        bsnLinkTestReceivedPktCount Integer32,
                        bsnLinkTestClientRSSI       Integer32,
                        bsnLinkTestLocalSNR         Integer32,
                        bsnLinkTestLocalRSSI        Integer32,
                        bsnLinkTestStatus           INTEGER,
                        bsnLinkTestRowStatus        RowStatus }

bsnLinkTestId OBJECT-TYPE
    SYNTAX Integer32 (0..24)
    MAX-ACCESS read-create
    STATUS deprecated
    DESCRIPTION
        "Link Test ID"
    ::= { bsnLinkTestEntry 1 }

bsnLinkTestMacAddress OBJECT-TYPE
    SYNTAX MacAddress
    MAX-ACCESS read-create
    STATUS deprecated
    DESCRIPTION
        "MAC Address of link to test"
    ::= { bsnLinkTestEntry 2 }

bsnLinkTestSendPktCount OBJECT-TYPE
    SYNTAX Integer32 (1..20)
    MAX-ACCESS read-create
    STATUS deprecated
    DESCRIPTION
        "Number of packets sent."
    DEFVAL {3}
    ::= { bsnLinkTestEntry 3 }

bsnLinkTestSendPktLength OBJECT-TYPE
    SYNTAX Integer32 (1..2000)
    MAX-ACCESS read-create
    STATUS deprecated
    DESCRIPTION
        "Length of sent packet"
    DEFVAL {500}
    ::= { bsnLinkTestEntry 4 }

bsnLinkTestReceivedPktCount OBJECT-TYPE
    SYNTAX Integer32
    MAX-ACCESS read-only
    STATUS deprecated
    DESCRIPTION
        "Number of received packets."
    ::= { bsnLinkTestEntry 5 }

bsnLinkTestClientRSSI OBJECT-TYPE
    SYNTAX Integer32
    MAX-ACCESS read-only
    STATUS deprecated
    DESCRIPTION
        "Client RSSI value of link."
    ::= { bsnLinkTestEntry 6 }

bsnLinkTestLocalSNR OBJECT-TYPE
    SYNTAX Integer32
    MAX-ACCESS read-only
    STATUS deprecated
    DESCRIPTION
        "Local SNR of the link"
    ::= { bsnLinkTestEntry 7 }

bsnLinkTestLocalRSSI OBJECT-TYPE
    SYNTAX Integer32
    MAX-ACCESS read-only
    STATUS deprecated
    DESCRIPTION
        "Local RSSI of the link."
    ::= { bsnLinkTestEntry 8 }

bsnLinkTestStatus OBJECT-TYPE
    SYNTAX INTEGER { inprogress(1), complete(2) }
    MAX-ACCESS read-only
    STATUS deprecated
    DESCRIPTION
        "Status of the link test."
    ::= { bsnLinkTestEntry 9 }

bsnLinkTestRowStatus OBJECT-TYPE
    SYNTAX RowStatus
    MAX-ACCESS read-create
    STATUS deprecated
    DESCRIPTION
        "Row Status"
    ::= { bsnLinkTestEntry 30 }

-- ********************************************************************
-- * Begin of bsnMobility
-- ********************************************************************
bsnMobilityConfig OBJECT IDENTIFIER ::= {bsnMobility 1}
bsnMobilityStats OBJECT IDENTIFIER ::= {bsnMobility 2}

bsnMobilityProtocolPortNum OBJECT-TYPE
        SYNTAX Integer32
        MAX-ACCESS read-write
        STATUS current
        DESCRIPTION
            "Port Number on which mobility Protocol runs"
        DEFVAL {0}
    ::= { bsnMobilityConfig 1 }

bsnMobilityDynamicDiscovery OBJECT-TYPE
        SYNTAX INTEGER {disable(0), enable(1)}
        MAX-ACCESS read-write
        STATUS current
        DESCRIPTION
            "Statically Configured is always enabled if members are 
             defined. To further enable rrm discovery, learned 
             discovery, broadcast discovery, enable/disable this 
             attribute."
    ::= { bsnMobilityConfig 3 }

bsnMobilityStatsReset OBJECT-TYPE
        SYNTAX INTEGER {default (0), resetNow(1)}
        MAX-ACCESS read-write
        STATUS current
        DESCRIPTION
            "Reset mobility statistics by setting this atribute to 
             resetNow. If you try to read this attribute value will 
             always be 0."
    ::= { bsnMobilityConfig 4 }

-- ********************************************************************
-- *    bsnMobilityGroupMembersTable
-- ********************************************************************

bsnMobilityGroupMembersTable OBJECT-TYPE
    SYNTAX SEQUENCE OF BsnMobilityGroupMembersEntry
    MAX-ACCESS not-accessible
    STATUS current
    DESCRIPTION
        "MWAR List (statically configured members of the mobility 
         group)"
    ::= { bsnMobilityConfig 10 }

bsnMobilityGroupMembersEntry OBJECT-TYPE
    SYNTAX BsnMobilityGroupMembersEntry
    MAX-ACCESS not-accessible
    STATUS current
    DESCRIPTION
        "An Entry (conceptual row) in the bsnMobilityGroupMembers
        Table."
    INDEX { bsnMobilityGroupMemberMacAddress }
    ::= { bsnMobilityGroupMembersTable  1 }

BsnMobilityGroupMembersEntry ::=
        SEQUENCE {      
        bsnMobilityGroupMemberMacAddress  MacAddress,
        bsnMobilityGroupMemberIPAddress   IpAddress,
        bsnMobilityGroupMemberGroupName   DisplayString,
        bsnMobilityGroupMemberRowStatus   RowStatus}

bsnMobilityGroupMemberMacAddress OBJECT-TYPE
    SYNTAX MacAddress
    MAX-ACCESS read-create
    STATUS current
    DESCRIPTION
        "Member switch MAC Address"
    ::= { bsnMobilityGroupMembersEntry 1 }

bsnMobilityGroupMemberIPAddress OBJECT-TYPE
    SYNTAX IpAddress
    MAX-ACCESS read-create
    STATUS current
    DESCRIPTION
        "Member switch IP Address"
    ::= { bsnMobilityGroupMembersEntry 2 }

bsnMobilityGroupMemberGroupName OBJECT-TYPE
    SYNTAX DisplayString (SIZE(0..31))
    MAX-ACCESS read-create
    STATUS current
    DESCRIPTION
        "Member's group name. If left empty while adding a new group 
         member, this assumes the default mobility group name of the 
         switch."
    ::= { bsnMobilityGroupMembersEntry 3 }

bsnMobilityGroupMemberRowStatus OBJECT-TYPE
    SYNTAX RowStatus
    MAX-ACCESS read-create
    STATUS current
    DESCRIPTION
        "Row Status"
    ::= { bsnMobilityGroupMembersEntry 22 }


-- ********************************************************************
-- *    bsnMobilityAnchorsTable
-- ********************************************************************

bsnMobilityAnchorsTable OBJECT-TYPE
    SYNTAX SEQUENCE OF BsnMobilityAnchorsEntry
    MAX-ACCESS not-accessible
    STATUS current
    DESCRIPTION
        "Statically configured mobility anchors"
    ::= { bsnMobilityConfig 11 }

bsnMobilityAnchorsEntry OBJECT-TYPE
    SYNTAX BsnMobilityAnchorsEntry
    MAX-ACCESS not-accessible
    STATUS current
    DESCRIPTION
        "An Entry (conceptual row) in the bsnMobilityAnchorsTable
        Table."
    INDEX { bsnMobilityAnchorWlanSsid, 
            bsnMobilityAnchorSwitchIPAddress }
    ::= { bsnMobilityAnchorsTable  1 }

BsnMobilityAnchorsEntry ::=
        SEQUENCE {      bsnMobilityAnchorWlanSsid        DisplayString,
                        bsnMobilityAnchorSwitchIPAddress IpAddress,
                        bsnMobilityAnchorRowStatus       RowStatus }

bsnMobilityAnchorWlanSsid OBJECT-TYPE
    SYNTAX DisplayString (SIZE(1..32))
    MAX-ACCESS read-create
    STATUS current
    DESCRIPTION
        "Local wlan-ssid to connect to Guest/Anchor switch"
    ::= { bsnMobilityAnchorsEntry 1 }

bsnMobilityAnchorSwitchIPAddress OBJECT-TYPE
    SYNTAX IpAddress
    MAX-ACCESS read-create
    STATUS current
    DESCRIPTION
        "Guest/Anchor switch IP Address"
    ::= { bsnMobilityAnchorsEntry 2 }

bsnMobilityAnchorRowStatus OBJECT-TYPE
    SYNTAX RowStatus
    MAX-ACCESS read-create
    STATUS current
    DESCRIPTION
        "Row Status"
    ::= { bsnMobilityAnchorsEntry 20 }


-- ********************************************************************
-- * Begin of bsnMobilityStats
-- ********************************************************************

bsnTotalHandoffRequests OBJECT-TYPE
        SYNTAX Counter32
        MAX-ACCESS read-only
        STATUS current
        DESCRIPTION
            "Total handoff requests"
    ::= { bsnMobilityStats 1 }

bsnTotalHandoffs OBJECT-TYPE
        SYNTAX Counter32
        MAX-ACCESS read-only
        STATUS current
        DESCRIPTION
            "Total handoffs"
    ::= { bsnMobilityStats 2 }

bsnCurrentExportedClients OBJECT-TYPE
        SYNTAX Counter32
        MAX-ACCESS read-only
        STATUS current
        DESCRIPTION
            "Current exported client count"
    ::= { bsnMobilityStats 3 }

bsnTotalExportedClients OBJECT-TYPE
        SYNTAX Counter32
        MAX-ACCESS read-only
        STATUS current
        DESCRIPTION
            "Total exported client count"
    ::= { bsnMobilityStats 4 }


bsnCurrentImportedClients OBJECT-TYPE
        SYNTAX Counter32
        MAX-ACCESS read-only
        STATUS current
        DESCRIPTION
            "Current Imported client count"
    ::= { bsnMobilityStats 5 }

bsnTotalImportedClients OBJECT-TYPE
        SYNTAX Counter32
        MAX-ACCESS read-only
        STATUS current
        DESCRIPTION
            "Total Imported client count"
    ::= { bsnMobilityStats 6 }

bsnTotalHandoffErrors OBJECT-TYPE
        SYNTAX Counter32
        MAX-ACCESS read-only
        STATUS current
        DESCRIPTION
            "Total handoff errors"
    ::= { bsnMobilityStats 7 }

bsnTotalCommunicationErrors OBJECT-TYPE
        SYNTAX Counter32
        MAX-ACCESS read-only
        STATUS current
        DESCRIPTION
            "Total communication errors"
    ::= { bsnMobilityStats 8 }

bsnTotalReceiveErrors OBJECT-TYPE
        SYNTAX Counter32
        MAX-ACCESS read-only
        STATUS current
        DESCRIPTION
            "Total receive errors"
    ::= { bsnMobilityStats 10 }

bsnTotalTransmitErrors OBJECT-TYPE
        SYNTAX Counter32
        MAX-ACCESS read-only
        STATUS current
        DESCRIPTION
            "Total Transmit errors"
    ::= { bsnMobilityStats 11 }

bsnTotalResponsesRetransmitted OBJECT-TYPE
        SYNTAX Counter32
        MAX-ACCESS read-only
        STATUS current
        DESCRIPTION
            "Total Responses Retransmitted"
    ::= { bsnMobilityStats 12 }

bsnTotalHandoffEndRequestsReceived OBJECT-TYPE
        SYNTAX Counter32
        MAX-ACCESS read-only
        STATUS current
        DESCRIPTION
            "Total Handoff End Requests Received"
    ::= { bsnMobilityStats 13 }

bsnTotalStateTransitionsDisallowed OBJECT-TYPE
        SYNTAX Counter32
        MAX-ACCESS read-only
        STATUS current
        DESCRIPTION
            "Total State Transitions Disallowed"
    ::= { bsnMobilityStats 14 }

bsnTotalResourceErrors OBJECT-TYPE
        SYNTAX Counter32
        MAX-ACCESS read-only
        STATUS current
        DESCRIPTION
            "Total Resource Errors"
    ::= { bsnMobilityStats 15 }

bsnTotalHandoffRequestsSent OBJECT-TYPE
        SYNTAX Counter32
        MAX-ACCESS read-only
        STATUS current
        DESCRIPTION
            "Total Handoff Requests Sent"
    ::= { bsnMobilityStats 16 }

bsnTotalHandoffRepliesReceived OBJECT-TYPE
        SYNTAX Counter32
        MAX-ACCESS read-only
        STATUS current
        DESCRIPTION
            "Total Handoff Replies Received"
    ::= { bsnMobilityStats 17 }

bsnTotalHandoffAsLocalReceived OBJECT-TYPE
        SYNTAX Counter32
        MAX-ACCESS read-only
        STATUS current
        DESCRIPTION
            "Total Handoffs As Local Received"
    ::= { bsnMobilityStats 18 }

bsnTotalHandoffAsForeignReceived OBJECT-TYPE
        SYNTAX Counter32
        MAX-ACCESS read-only
        STATUS current
        DESCRIPTION
            "Total Handoffs As Foreign Received"
    ::= { bsnMobilityStats 19 }

bsnTotalHandoffDeniesReceived OBJECT-TYPE
        SYNTAX Counter32
        MAX-ACCESS read-only
        STATUS current
        DESCRIPTION
            "Total Handoff Denies Received"
    ::= { bsnMobilityStats 20 }

bsnTotalAnchorRequestsSent OBJECT-TYPE
        SYNTAX Counter32
        MAX-ACCESS read-only
        STATUS current
        DESCRIPTION
            "Total Anchor Requests Sent"
    ::= { bsnMobilityStats 21 }

bsnTotalAnchorDenyReceived OBJECT-TYPE
        SYNTAX Counter32
        MAX-ACCESS read-only
        STATUS current
        DESCRIPTION
            "Total Anchor Deny Received"
    ::= { bsnMobilityStats 22 }

bsnTotalAnchorGrantReceived OBJECT-TYPE
        SYNTAX Counter32
        MAX-ACCESS read-only
        STATUS current
        DESCRIPTION
            "Total Anchor Grant Received"
    ::= { bsnMobilityStats 23 }

bsnTotalAnchorTransferReceived OBJECT-TYPE
        SYNTAX Counter32
        MAX-ACCESS read-only
        STATUS current
        DESCRIPTION
            "Total Anchor Transfer Received"
    ::= { bsnMobilityStats 24 }

bsnTotalHandoffRequestsIgnored OBJECT-TYPE
        SYNTAX Counter32
        MAX-ACCESS read-only
        STATUS current
        DESCRIPTION
            "Total Handoff Requests Ignored"
    ::= { bsnMobilityStats 25 }

bsnTotalPingPongHandoffRequestsDropped OBJECT-TYPE
        SYNTAX Counter32
        MAX-ACCESS read-only
        STATUS current
        DESCRIPTION
            "Total Ping Pong Handoff Requests Dropped"
    ::= { bsnMobilityStats 26 }

bsnTotalHandoffRequestsDropped OBJECT-TYPE
        SYNTAX Counter32
        MAX-ACCESS read-only
        STATUS current
        DESCRIPTION
            "Total Handoff Requests Dropped"
    ::= { bsnMobilityStats 27 }

bsnTotalHandoffRequestsDenied OBJECT-TYPE
        SYNTAX Counter32
        MAX-ACCESS read-only
        STATUS current
        DESCRIPTION
            "Total Handoff Requests Denied"
    ::= { bsnMobilityStats 28 }

bsnTotalClientHandoffAsLocal OBJECT-TYPE
        SYNTAX Counter32
        MAX-ACCESS read-only
        STATUS current
        DESCRIPTION
            "Total Client Handoffs As Local"
    ::= { bsnMobilityStats 29 }

bsnTotalClientHandoffAsForeign OBJECT-TYPE
        SYNTAX Counter32
        MAX-ACCESS read-only
        STATUS current
        DESCRIPTION
            "Total Client Handoffs As Foreign"
    ::= { bsnMobilityStats 30 }

bsnTotalAnchorRequestsReceived OBJECT-TYPE
        SYNTAX Counter32
        MAX-ACCESS read-only
        STATUS current
        DESCRIPTION
            "Total Anchor Requests Received"
    ::= { bsnMobilityStats 31 }

bsnTotalAnchorRequestsDenied OBJECT-TYPE
        SYNTAX Counter32
        MAX-ACCESS read-only
        STATUS current
        DESCRIPTION
            "Total Anchor Requests Denied"
    ::= { bsnMobilityStats 32 }

bsnTotalAnchorRequestsGranted OBJECT-TYPE
        SYNTAX Counter32
        MAX-ACCESS read-only
        STATUS current
        DESCRIPTION
            "Total Anchor Requests Granted"
    ::= { bsnMobilityStats 33 }

bsnTotalAnchorTransferred OBJECT-TYPE
        SYNTAX Counter32
        MAX-ACCESS read-only
        STATUS current
        DESCRIPTION
            "Total Anchor Transferred"
    ::= { bsnMobilityStats 34 }

bsnTotalHandoffRequestsReceived OBJECT-TYPE
        SYNTAX Counter32
        MAX-ACCESS read-only
        STATUS current
        DESCRIPTION
            "Total Handoff Requests Received"
    ::= { bsnMobilityStats 35 }


-- ********************************************************************
-- *    bsnMobilityGroupDirectoryTable
-- ********************************************************************

bsnMobilityGroupDirectoryTable OBJECT-TYPE
    SYNTAX SEQUENCE OF BsnMobilityGroupDirectoryEntry
    MAX-ACCESS not-accessible
    STATUS current
    DESCRIPTION
        "MWAR List (statically configured members of the mobility 
         group)"
    ::= { bsnMobilityStats 9 }

bsnMobilityGroupDirectoryEntry OBJECT-TYPE
    SYNTAX BsnMobilityGroupDirectoryEntry
    MAX-ACCESS not-accessible
    STATUS current
    DESCRIPTION
        "An Entry (conceptual row) in the bsnMobilityGroupDirectory
        Table."
    INDEX { bsnGroupDirectoryMemberMacAddress }
    ::= { bsnMobilityGroupDirectoryTable  1 }

BsnMobilityGroupDirectoryEntry ::=
        SEQUENCE {      bsnGroupDirectoryMemberIPAddress   IpAddress,
                        bsnGroupDirectoryMemberMacAddress  MacAddress,
                        bsnGroupDirectoryDicoveryType      INTEGER,
                        bsnMemberCurrentAnchoredClients    Counter32,
                        bsnMemberTotalAnchoredClients      Counter32,
                        bsnMemberCurrentExportedClients    Counter32,
                        bsnMemberTotalExportedClients      Counter32,
                        bsnMemberCurrentImportedClients    Counter32,
                        bsnMemberTotalImportedClients      Counter32,
                        bsnMemberTotalHandoffErrors        Counter32,
                        bsnMemberTotalCommunicationErrors  Counter32 }

bsnGroupDirectoryMemberIPAddress OBJECT-TYPE
    SYNTAX IpAddress
    MAX-ACCESS read-only
    STATUS current
    DESCRIPTION
        "Mwar Ip Address"
    ::= { bsnMobilityGroupDirectoryEntry 1 }

bsnGroupDirectoryMemberMacAddress OBJECT-TYPE
    SYNTAX MacAddress
    MAX-ACCESS read-only
    STATUS current
    DESCRIPTION
        "Mwar Mac Address"
    ::= { bsnMobilityGroupDirectoryEntry 2 }

bsnGroupDirectoryDicoveryType OBJECT-TYPE
    SYNTAX INTEGER { static (1), rrm (2),
                     broadcast (3), learned (4) }
    MAX-ACCESS read-only
    STATUS current
    DESCRIPTION
        "Discovery type of the Group Directory."
    ::= { bsnMobilityGroupDirectoryEntry 3 }

bsnMemberCurrentAnchoredClients OBJECT-TYPE
        SYNTAX Counter32
        MAX-ACCESS read-only
        STATUS current
        DESCRIPTION
            "Current anchored client count"
    ::= { bsnMobilityGroupDirectoryEntry  4 }

bsnMemberTotalAnchoredClients OBJECT-TYPE
        SYNTAX Counter32
        MAX-ACCESS read-only
        STATUS current
        DESCRIPTION
            "Total anchored client count"
    ::= { bsnMobilityGroupDirectoryEntry 5 }

bsnMemberCurrentExportedClients OBJECT-TYPE
        SYNTAX Counter32
        MAX-ACCESS read-only
        STATUS current
        DESCRIPTION
            "Current exported client count"
    ::= { bsnMobilityGroupDirectoryEntry 6 }

bsnMemberTotalExportedClients OBJECT-TYPE
        SYNTAX Counter32
        MAX-ACCESS read-only
        STATUS current
        DESCRIPTION
            "Total exported client count"
    ::= { bsnMobilityGroupDirectoryEntry 7 }


bsnMemberCurrentImportedClients OBJECT-TYPE
        SYNTAX Counter32
        MAX-ACCESS read-only
        STATUS current
        DESCRIPTION
            "Current Imported client count"
    ::= { bsnMobilityGroupDirectoryEntry 8 }

bsnMemberTotalImportedClients OBJECT-TYPE
        SYNTAX Counter32
        MAX-ACCESS read-only
        STATUS current
        DESCRIPTION
            "Total Imported client count"
    ::= { bsnMobilityGroupDirectoryEntry 9 }

bsnMemberTotalHandoffErrors OBJECT-TYPE
        SYNTAX Counter32
        MAX-ACCESS read-only
        STATUS current
        DESCRIPTION
            "Total handoff errors"
    ::= { bsnMobilityGroupDirectoryEntry 10 }

bsnMemberTotalCommunicationErrors OBJECT-TYPE
        SYNTAX Counter32
        MAX-ACCESS read-only
        STATUS current
        DESCRIPTION
            "Total Communication errors"
    ::= { bsnMobilityGroupDirectoryEntry 30 }

    bsnAPGroupsVlanConfig OBJECT IDENTIFIER ::= { bsnWireless 10}

-- ********************************************************************
--  Airespace Site Specific WLAN Configuration Paramaters
--  DEFINED AS "The bsnAPGroupsVlanConfig object provides all the
--  configuration and monitoring of Site Specific WLAN ";
-- ********************************************************************

bsnAPGroupsVlanFeature OBJECT-TYPE
        SYNTAX INTEGER { disable(0), enable(1)}
        MAX-ACCESS read-write
        STATUS current
        DESCRIPTION
            "When enabled, Site Specific WLAN feature is enforced."
        ::= { bsnAPGroupsVlanConfig 1 }


-- ********************************************************************
-- * Begin of bsnAPGroupsVlanTable
-- ********************************************************************

bsnAPGroupsVlanTable OBJECT-TYPE
    SYNTAX SEQUENCE OF BsnAPGroupsVlanEntry
    MAX-ACCESS not-accessible
    STATUS current
    DESCRIPTION
        "Wireless Sites Table."
    ::= { bsnAPGroupsVlanConfig 2 }

bsnAPGroupsVlanEntry OBJECT-TYPE
    SYNTAX BsnAPGroupsVlanEntry
    MAX-ACCESS not-accessible
    STATUS current
    DESCRIPTION
        "An entry in bsnAPGroupsVlanTable."
    INDEX { bsnAPGroupsVlanName }
    ::= { bsnAPGroupsVlanTable 1 }

BsnAPGroupsVlanEntry ::=
    SEQUENCE {
        bsnAPGroupsVlanName        OCTET STRING,          
        bsnAPGroupsVlanDescription OCTET STRING,          
        bsnAPGroupsVlanRowStatus   RowStatus          
    }

bsnAPGroupsVlanName OBJECT-TYPE
        SYNTAX OCTET STRING (SIZE(1..31))
        MAX-ACCESS read-create
        STATUS current
        DESCRIPTION
          "The string is an unique identifier/name assigned to a site."
    ::= { bsnAPGroupsVlanEntry 1}

bsnAPGroupsVlanDescription OBJECT-TYPE
        SYNTAX OCTET STRING (SIZE(0..31))
        MAX-ACCESS read-create
        STATUS current
        DESCRIPTION
           "Description about the site."
    ::= { bsnAPGroupsVlanEntry 2}

bsnAPGroupsVlanRowStatus  OBJECT-TYPE
      SYNTAX RowStatus
      MAX-ACCESS read-create
      STATUS current
      DESCRIPTION
         "Row Status for creation/deletion of entries in 
          bsnAPGroupsVlanTable"
      ::= { bsnAPGroupsVlanEntry 20 }


-- ********************************************************************
-- * Begin of bsnAPGroupsVlanMappingTable
-- ********************************************************************

bsnAPGroupsVlanMappingTable OBJECT-TYPE
    SYNTAX SEQUENCE OF BsnAPGroupsVlanMappingEntry
    MAX-ACCESS not-accessible
    STATUS current
    DESCRIPTION
        "A table for the WLAN-interace-mappings allowed for each 
         configured site. Each site can have a set of WLANs associated
         with it."
    ::= { bsnAPGroupsVlanConfig 3 }

bsnAPGroupsVlanMappingEntry OBJECT-TYPE
    SYNTAX BsnAPGroupsVlanMappingEntry
    MAX-ACCESS not-accessible
    STATUS current
    DESCRIPTION
        "An entry in bsnAPGroupsVlanMappingTable."
    INDEX { bsnAPGroupsVlanName, bsnAPGroupsVlanMappingSsid }
    ::= { bsnAPGroupsVlanMappingTable 1 }

BsnAPGroupsVlanMappingEntry ::=
    SEQUENCE {
        bsnAPGroupsVlanMappingSsid DisplayString,
        bsnAPGroupsVlanMappingInterfaceName OCTET STRING,
        bsnAPGroupsVlanMappingRowStatus RowStatus
    }

bsnAPGroupsVlanMappingSsid OBJECT-TYPE
        SYNTAX DisplayString (SIZE(1..32))
        MAX-ACCESS read-create
        STATUS current
        DESCRIPTION
                "When an AP is associated with a site, and the site
        has an associated set of WLANs, then only those WLANs are
        beamed by the AP. Here 'bsnAPGroupsVlanMappingSsid'
        is the wlan to be used when a client connects on this AP."
    ::= { bsnAPGroupsVlanMappingEntry 1}

bsnAPGroupsVlanMappingInterfaceName OBJECT-TYPE
        SYNTAX OCTET STRING (SIZE(1..32))
        MAX-ACCESS read-create
        STATUS current
        DESCRIPTION
                "When an AP is associated with a site, and the site 
        has an associated set of WLANs, then only those WLANs are 
        beamed by the AP. Here 'bsnAPGroupsVlanMappingInterfaceName'
        is the interface to be used when a client connects to the
        'bsnAPGroupsVlanMappingSsid' WLAN on this AP."
    ::= { bsnAPGroupsVlanMappingEntry 2}

bsnAPGroupsVlanMappingRowStatus  OBJECT-TYPE
      SYNTAX RowStatus
      MAX-ACCESS read-create
      STATUS current
      DESCRIPTION
           "Row Status for creation/deletion of WLAN-interface-mappings
            asscoiated with sites."
      ::= { bsnAPGroupsVlanMappingEntry 20 }

bsnAPIPAddressFallback NOTIFICATION-TYPE
    OBJECTS { bsnAPDot3MacAddress, bsnApIpAddress, bsnAPStaticIPAddress }
    STATUS current
    DESCRIPTION
        "This trap is sent out when an AP, with the configured static 
         ip-address, fails to establish connection with outside world 
         and starts using DHCP as a fallback option."
    ::= { bsnTraps 77 }

bsnAPFunctionalityDisabled NOTIFICATION-TYPE
    OBJECTS { bsnApFunctionalityDisableReasonCode, 
              bsnLicenseKeyTrapVariable, 
              bsnLicenseKeyFeatureSetTrapVariable }
    STATUS current
    DESCRIPTION
        "This trap is sent out when AP functionality on the switch is 
         disabled because the License key has expired
         or has been deleted or doesn't match the switch image."
    ::= { bsnTraps 78 }

bsnLicenseKeyTrapVariable OBJECT-TYPE
    SYNTAX  OCTET STRING (SIZE(0..255))
    MAX-ACCESS  accessible-for-notify
    STATUS  current
    DESCRIPTION
            "This is the license key that has been found to be deleted,
             expired or is mismatched causing AP
             functionality to be disabled on the switch."
    ::= { bsnTrapVariable 65 }

bsnApFunctionalityDisableReasonCode OBJECT-TYPE
    SYNTAX  INTEGER { unknown (0), licenseKeyExpired (1), 
                      licenseKeyDeleted (2), 
                      licenseKeyFeatureMismatch (3)}
    MAX-ACCESS  accessible-for-notify
    STATUS  current
    DESCRIPTION
            "This is the reason why the AP functionality was disabled 
             on the switch. It could be either expiry or deletion or 
             mismatch found of the license key."
    ::= { bsnTrapVariable 66 }

bsnLicenseKeyFeatureSetTrapVariable OBJECT-TYPE
    SYNTAX  INTEGER { wps (1), all (2) }
    MAX-ACCESS  accessible-for-notify
    STATUS  current
    DESCRIPTION
            "This is the switch feature set whose license key has 
             expired or is deleted or is mismatched.
             To enable the AP functionality again, the license key for
             this feature set should be re-configured."
    ::= { bsnTrapVariable 67 }

bsnRxMulticastQueueFull NOTIFICATION-TYPE
    STATUS current
    DESCRIPTION
       "This trap indicates that the CPU's Receive Multicast Queue is
        Full."
    ::= { bsnTraps 80 }


bsnAPAuthorizationFailureCause OBJECT-TYPE
    SYNTAX  INTEGER { unknown (0), 
                      keymismatch (1), 
                      entrydoesnotexist (2),
                      invalidCertifcate (3),
                      entryIsMIC(4)}
    MAX-ACCESS  accessible-for-notify
    STATUS  current
    DESCRIPTION
        "This denotes the reason for AP authorization failure.
        [entrydoesnotexist]:  
                        The AP has not been added to Controller's
                        AP Authorization List.
        [keymismatch]:  The key entry in Controller's AP Authorization 
                        list does not match the SHA1 key received from 
                        the AP.
        [invalidCert]:  Could not verify the self signed Certificate.
        [entryIsMIC]:   AP has Self Signed Certificate where as in 
                        Controller AP Authorization list has 
                        Manufactured Installed Certificate
        [unknown]:      Default.
        "
    ::= { bsnTrapVariable 69 }

bsnAPIfUpDownCause OBJECT-TYPE
    SYNTAX  INTEGER { unknown (0), 
                      radioFailure (1), 
                      radioLowPower (2),
                      maxRetransmission (3),
                      echoTimeout (4),
                      configAP (5),
                      configRadio (6),
                      configNetwork (7)}
    MAX-ACCESS  accessible-for-notify
    STATUS  current
    DESCRIPTION
        "This denotes the reason for AP If up or down
         normal - 
         radio Failure - radio failed
         radioLowPower - AP is not able draw enough power.
         maxRetransmission - max retransmission of AP Reached.
         echoTimeout - heartbeat timeout.
         configAP - admin enable/disable AP
         configRadio - admin enable/disable config radio
         configNetwork - admin enable/disable network
        "
    ::= { bsnTrapVariable 70 }

bsnAPInvalidRadioType OBJECT-TYPE
    SYNTAX  INTEGER { unsupportedRadio (0)}
    MAX-ACCESS  accessible-for-notify
    STATUS  current
    DESCRIPTION
        "Radio types which are not supported by controller." 
    ::= { bsnTrapVariable 71 }
    
locationNotifyContent OBJECT-TYPE
    SYNTAX  OCTET STRING (SIZE(0..512))
    MAX-ACCESS  accessible-for-notify
    STATUS  current
    DESCRIPTION
        "This is the content of the notification." 
    ::= { bsnTrapVariable 72 }    

bsnSignatureMacInfo OBJECT-TYPE
    SYNTAX BsnTxtSignatureMacInfo
    MAX-ACCESS accessible-for-notify
    STATUS current
    DESCRIPTION
                "This object defines the pattern followed by the
                LWAPP APs to perform signature analysis with this
                signature and report the results to the
                Controller. "
    ::= { bsnTrapVariable 73 }

bsnRadarChannelDetected NOTIFICATION-TYPE
    OBJECTS { bsnAPDot3MacAddress, bsnAPIfSlotId, bsnAPIfPhyChannelNumber}
    STATUS current
    DESCRIPTION
        "This trap is sent when radar signals are detected on the 
         current channel"
    ::= { bsnTraps 81 }

bsnRadarChannelCleared NOTIFICATION-TYPE
    OBJECTS { bsnAPDot3MacAddress, bsnAPIfSlotId, bsnAPIfPhyChannelNumber}
    STATUS current
    DESCRIPTION
        "This trap will be generated, if a radar trap has been 
         generated earlier, after the expiry of Non-Occupancy Period."
    ::= { bsnTraps 82 }

bsnAPAuthorizationFailure NOTIFICATION-TYPE
    OBJECTS { bsnAPDot3MacAddress, bsnAPName, 
              bsnAPAuthCertificateType,bsnAPAuthorizationFailureCause }
    STATUS current
    DESCRIPTION
        "This trap is sent out in case of authorization failure while 
         attempting to associate the AP to the controller.
         bsnAPDot3MacAddress represents the mac-address of that AP.
         bsnAPName is name of AP"
    ::= { bsnTraps 83 }

radioCoreDumpTrap NOTIFICATION-TYPE
    OBJECTS { bsnAPDot3MacAddress, bsnAPIfSlotId }
    STATUS current
    DESCRIPTION
        "When radio module in AP dumps core, it informs controller and 
         controller generates this trap. The core file can be retrieved
         on demand."
    ::= { bsnTraps 84 }


invalidRadioTrap NOTIFICATION-TYPE
    OBJECTS { bsnAPDot3MacAddress, bsnAPIfSlotId, 
              bsnAPInvalidRadioType }
    STATUS current
    DESCRIPTION
        "This trap will be generated when an AP has joined is using 
         unsupported radio or a radio slot not currently not being 
         used."
    ::= { bsnTraps 85 }

countryChangeTrap NOTIFICATION-TYPE
    OBJECTS { bsnGlobalDot11CountryIndex }
    STATUS current
    DESCRIPTION
        "This trap will be generated when an operator changes the
         country of operation. New country code will be sent in trap."
    ::= { bsnTraps 86 }

unsupportedAPTrap  NOTIFICATION-TYPE
    OBJECTS { bsnAPDot3MacAddress, bsnAPName}
    STATUS current
    DESCRIPTION
        "This trap will be generated when unsupported AP try to join
         40xx/410x or 3500 with 64MB flash." 
    ::= { bsnTraps 87 }

heartbeatLossTrap  NOTIFICATION-TYPE
    STATUS current
    DESCRIPTION
        "This trap will be generated when controller loses 
        connection with the Supervisor Switch in which it
        is physically embedded and doesn't hear the
        heartbeat keepalives from the Supervisor. "
    ::= { bsnTraps 88 }
    
locationNotifyTrap  NOTIFICATION-TYPE
    OBJECTS { locationNotifyContent}
    STATUS current
    DESCRIPTION
        "This trap will be generated by the location server 
        for notifications of location events." 
    ::= { bsnTraps 89 }

--********************************************************************
--*    Compliance statements
--********************************************************************
bsnWrasCompliance MODULE-COMPLIANCE
    STATUS  current
    DESCRIPTION
        "The compliance statement for the SNMP entities that
         implement the bsnWireless module."
    MODULE
        MANDATORY-GROUPS { bsnEssGroup,
                           bsnApGroup,
                           bsnGlobalDot11Group,
                           bsnRrmGroup,
                           bsnAAAGroup,
                           bsnTrapsGroup,
                           bsnUtilityGroup,
                           bsnMobilityGroup,
                           bsnIpsecGroup }
    ::= { bsnWrasCompliances 1 }


--********************************************************************
--*    Units of conformance
--********************************************************************

bsnEssGroup OBJECT-GROUP
    OBJECTS {

--Begin bsnDot11EssTable 
        bsnDot11EssIndex,
        bsnDot11EssSsid,
        bsnDot11EssSessionTimeout,
        bsnDot11EssMacFiltering,
        bsnDot11EssAdminStatus,
        bsnDot11EssSecurityAuthType,
        bsnDot11EssStaticWEPSecurity,
        bsnDot11EssStaticWEPEncryptionType,
        bsnDot11EssStaticWEPDefaultKey,
        bsnDot11EssStaticWEPKeyIndex,
        bsnDot11EssStaticWEPKeyFormat,
        bsnDot11Ess8021xSecurity,
        bsnDot11Ess8021xEncryptionType,
        bsnDot11EssIpsecSecurity,
        bsnDot11EssVpnEncrTransform,
        bsnDot11EssVpnAuthTransform,
        bsnDot11EssVpnIkeAuthMode,
        bsnDot11EssVpnSharedKey,
        bsnDot11EssVpnSharedKeySize,
        bsnDot11EssVpnIkePhase1Mode,
        bsnDot11EssVpnIkeLifetime,
        bsnDot11EssVpnIkeDHGroup,        
        bsnDot11EssIpsecPassthruSecurity,
        bsnDot11EssVpnPassthruGateway,
        bsnDot11EssWebSecurity,
        bsnDot11EssRadioPolicy,
        bsnDot11EssQualityOfService,
        bsnDot11EssDhcpRequired,
        bsnDot11EssDhcpServerIpAddress,
        bsnDot11EssVpnContivityMode,
        bsnDot11EssVpnQotdServerAddress,
        bsnDot11EssBlacklistTimeout,
        bsnDot11EssNumberOfMobileStations,
        bsnDot11EssWebPassthru,
        bsnDot11EssCraniteSecurity,
        bsnDot11EssBlacklistingCapability,
        bsnDot11EssInterfaceName,
        bsnDot11EssAclName,
        bsnDot11EssAAAOverride,
        bsnDot11EssWepAllowSharedKeyAuth,
        bsnDot11EssFortressSecurity,
        bsnDot11EssL2tpSecurity,
        bsnDot11EssBroadcastSsid,
        bsnDot11EssExternalPolicyValidation,
        bsnDot11EssIPv6Bridging,
        bsnDot11EssRowStatus,
        bsnDot11EssWmePolicySetting,
        bsnDot11Ess80211ePolicySetting,
        bsnDot11EssWebPassthroughEmail,
        bsnDot11Ess7920PhoneSupport,
        bsnDot11EssRadiusAuthPrimaryServer,
        bsnDot11EssRadiusAuthSecondaryServer,
        bsnDot11EssRadiusAuthTertiaryServer,
        bsnDot11EssRadiusAcctPrimaryServer,
        bsnDot11EssRadiusAcctSecondaryServer,
        bsnDot11EssRadiusAcctTertiaryServer,

--Begin bsnMobileStationTable 
        bsnMobileStationMacAddress,
        bsnMobileStationIpAddress,
        bsnMobileStationUserName,
        bsnMobileStationAPMacAddr,
        bsnMobileStationAPIfSlotId,
        bsnMobileStationEssIndex,
        bsnMobileStationSsid,
        bsnMobileStationStatus,
        bsnMobileStationReasonCode,
        bsnMobileStationMobilityStatus,
        bsnMobileStationAID,
        bsnMobileStationAnchorAddress,
        bsnMobileStationCFPollable,
        bsnMobileStationCFPollRequest,
        bsnMobileStationChannelAgilityEnabled,
        bsnMobileStationPBCCOptionImplemented,
        bsnMobileStationShortPreambleOptionImplemented,
        bsnMobileStationSessionTimeout,
        bsnMobileStationAuthenticationAlgorithm,
        bsnMobileStationWepState,
        bsnMobileStationPortNumber,
        bsnMobileStationDeleteAction,
        bsnMobileStationPolicyManagerState,
        bsnMobileStationSecurityPolicyStatus,
        bsnMobileStationProtocol,
        bsnMobileStationMirrorMode,
        bsnMobileStationInterface,
        bsnMobileStationApMode,
        bsnMobileStationVlanId,
        bsnMobileStationPolicyType,
        bsnMobileStationEncryptionCypher,
        bsnMobileStationEapType,
        bsnMobileStationCcxVersion,
        bsnMobileStationE2eVersion,
        bsnMobileStationStatusCode,

--Begin bsnMobileStationPerRadioPerVapTable 
        bsnMobileStationPerRadioPerVapIndex,
        bsnMobileStationMacAddr,

--Begin bsnMobileStationStatsTable 
        bsnMobileStationRSSI,
        bsnMobileStationBytesReceived,
        bsnMobileStationBytesSent,
        bsnMobileStationPolicyErrors,
        bsnMobileStationPacketsReceived,
        bsnMobileStationPacketsSent,
        bsnMobileStationSnr,

--Begin bsnRougeAPTable 
        bsnRogueAPDot11MacAddress,
        bsnRogueAPTotalDetectingAPs,
        bsnRogueAPFirstReported,
        bsnRogueAPLastReported,
        bsnRogueAPContainmentLevel,
        bsnRogueAPType,
        bsnRogueAPOnNetwork,
        bsnRogueAPTotalClients,
        bsnRogueAPRowStatus,
        bsnRogueAPMaxDetectedRSSI,
        bsnRogueAPSSID,
        bsnRogueAPState,


--Begin bsnRougeAPAirespaceAPTable 
        bsnRogueAPAirespaceAPMacAddress,
        bsnRogueAPAirespaceAPSlotId,
        bsnRogueAPRadioType,
        bsnRogueAPAirespaceAPName,
        bsnRogueAPChannelNumber,
        bsnRogueAPSsid,
        bsnRogueAPAirespaceAPRSSI,
        bsnRogueAPContainmentMode,
        bsnRogueAPContainmentChannelCount,
        bsnRogueAPContainmentChannels,
        bsnRogueAPAirespaceAPLastHeard,
        bsnRogueAPAirespaceAPWepMode,
        bsnRogueAPAirespaceAPPreamble,
        bsnRogueAPAirespaceAPWpaMode,
        bsnRogueAPAirespaceAPSNR,

--Begin bsnMobileStationByIpAddressTable 
        bsnMobileStationByIpAddress,
        bsnMobileStationByIpMacAddress,

--Begin bsnMobileStationRssiDataTable 
        bsnMobileStationRssiDataApMacAddress,
        bsnMobileStationRssiDataApIfSlotId,
        bsnMobileStationRssiDataApIfType,
        bsnMobileStationRssiDataApName,
        bsnMobileStationRssiData,
        bsnAPIfPhyAntennaIndex,
        bsnMobileStationRssiDataLastHeard,

--Begin bsnMobileStationByUsernameTable 
        bsnMobileStationByUserName,
        bsnMobileStationByUserMacAddress,

--Begin bsnRougeClientAirespaceAPTable 
        bsnRogueClientAirespaceAPMacAddress,
        bsnRogueClientAirespaceAPSlotId,
        bsnRogueClientRadioType,
        bsnRogueClientAirespaceAPName,
        bsnRogueClientChannelNumber,
        bsnRogueClientAirespaceAPRSSI,
        bsnRogueClientAirespaceAPLastHeard,
        bsnRogueClientAirespaceAPSNR,

--Begin bsnRougeClientTable 
        bsnRogueClientTotalDetectingAPs,
        bsnRogueClientFirstReported,
        bsnRogueClientLastReported,
        bsnRogueClientBSSID,
        bsnRogueClientContainmentLevel,
        bsnRogueClientLastHeard,
        bsnRogueClientState,

--Begin bsnRougeClientPerRougeAPTable 
        bsnRogueAPDot11MacAddr,
        bsnRogueClientDot11MacAddr,

--Begin bsnDot11QosProfileTable  
        bsnDot11QosProfileName,
        bsnDot11QosProfileDesc,
        bsnDot11QosAverageDataRate,
        bsnDot11QosBurstDataRate,
        bsnDot11QosAvgRealTimeDataRate,
        bsnDot11QosBurstRealTimeDataRate,
        bsnDot11QosMaxRFUsagePerAP,
        bsnDot11QosProfileQueueDepth,
        bsnDot11WiredQosProtocol,
        bsnDot11802Dot1PTag,
        bsnDot11ResetProfileToDefault,

--Begin bsnTagTable  
        bsnTagDot11MacAddress,
        bsnTagType,
        bsnTagTimeInterval,
        bsnTagBatteryStatus,
        bsnTagLastReported,

--Begin bsnTagRssiDataTable 
        bsnTagRssiDataApMacAddress,
        bsnTagRssiDataApIfSlotId,
        bsnTagRssiDataApIfType,
        bsnTagRssiDataApName,
        bsnTagRssiDataLastHeard,
        bsnTagRssiData,
        bsnTagRssiDataSnr,

--Begin bsnTagStatsTable      
        bsnTagBytesReceived,
        bsnTagPacketsReceived,

--Begin bsnMobileStationExtStatsTable 
        bsnMobileStationSampleTime,
        bsnMobileStationTxExcessiveRetries,
        bsnMobileStationTxRetries,
        bsnMobileStationTxFiltered
    }
    STATUS      current
    DESCRIPTION
        "This collection of objects provides information
         about Airespace Wireless LAN Configuration Attributes
         These objects are defined under bsnEss object."
    ::= { bsnWrasGroups 1 }

bsnApGroup OBJECT-GROUP
    OBJECTS {

--Begin bsnAPTable 
        bsnAPDot3MacAddress,
        bsnAPNumOfSlots,
        bsnAPName,
        bsnAPLocation,
        bsnAPMonitorOnlyMode,
        bsnAPOperationStatus,
        bsnAPSoftwareVersion,
        bsnAPBootVersion,
        bsnAPPrimaryMwarName,
        bsnAPReset,
        bsnAPStatsTimer,
        bsnAPPortNumber,
        bsnAPModel,
        bsnAPSerialNumber,
        bsnAPClearConfig,
        bsnApIpAddress,
        bsnAPMirrorMode,
        bsnAPRemoteModeSupport,
        bsnAPType,
        bsnAPSecondaryMwarName,
        bsnAPTertiaryMwarName,
        bsnAPIsStaticIP,
        bsnAPNetmask,
        bsnAPGateway,
        bsnAPStaticIPAddress,
        bsnAPBridgingSupport,
        bsnAPGroupVlanName,
        bsnAPIOSVersion,
        bsnAPCertificateType,
        bsnAPEthernetMacAddress,
        bsnAPAdminStatus,

--Begin bsnAPIfTable
        bsnAPIfSlotId,
        bsnAPIfType,
        bsnAPIfPhyChannelAssignment,
        bsnAPIfPhyChannelNumber,
        bsnAPIfPhyTxPowerControl,
        bsnAPIfPhyTxPowerLevel,
        bsnAPIfPhyAntennaMode,
        bsnAPIfPhyAntennaType,
        bsnAPIfPhyAntennaDiversity,
        bsnAPIfCellSiteConfigId,
        bsnAPIfNumberOfVaps,
        bsnAPIfOperStatus,
        bsnAPIfPortNumber,
        bsnAPIfPhyAntennaOptions,
        bsnApIfNoOfUsers,
        bsnAPIfWlanOverride,
        bsnAPIfPacketsSniffingFeature,
        bsnAPIfSniffChannel,
        bsnAPIfSniffServerIPAddress,
        bsnAPIfAntennaGain,
        bsnAPIfChannelList,
        bsnAPIfAbsolutePowerList,
        bsnAPIfRegulatoryDomainSupport,
        bsnAPIfAdminStatus,

--Begin bsnAPIfSmtParamTable
        bsnAPIfDot11BeaconPeriod,
        bsnAPIfDot11MediumOccupancyLimit,
        bsnAPIfDot11CFPPeriod,
        bsnAPIfDot11CFPMaxDuration,
        bsnAPIfDot11OperationalRateSet,
        bsnAPIfDot11DTIMPeriod,
        bsnAPIfDot11MultiDomainCapabilityImplemented,
        bsnAPIfDot11MultiDomainCapabilityEnabled,
        bsnAPIfDot11CountryString,
        bsnAPIfDot11SmtParamsConfigType,
        bsnAPIfDot11BSSID,

--Begin bsnAPIfMultiDomainCapabilityTable
        bsnAPIfDot11MaximumTransmitPowerLevel,
        bsnAPIfDot11FirstChannelNumber,
        bsnAPIfDot11NumberofChannels,

--Begin bsnAPIfMacOperationParamEntry
        bsnAPIfDot11MacRTSThreshold,
        bsnAPIfDot11MacShortRetryLimit,
        bsnAPIfDot11MacLongRetryLimit,
        bsnAPIfDot11MacFragmentationThreshold,
        bsnAPIfDot11MacMaxTransmitMSDULifetime,
        bsnAPIfDot11MacParamsConfigType,
        bsnAPIfDot11MacMaxReceiveLifetime,

--Begin bsnAPIfDot11CountersTable
        bsnAPIfDot11TransmittedFragmentCount,
        bsnAPIfDot11MulticastTransmittedFrameCount,
        bsnAPIfDot11RetryCount,
        bsnAPIfDot11MultipleRetryCount,
        bsnAPIfDot11FrameDuplicateCount,
        bsnAPIfDot11RTSSuccessCount,
        bsnAPIfDot11RTSFailureCount,
        bsnAPIfDot11ACKFailureCount,
        bsnAPIfDot11ReceivedFragmentCount,
        bsnAPIfDot11MulticastReceivedFrameCount,
        bsnAPIfDot11FCSErrorCount,
        bsnAPIfDot11TransmittedFrameCount,
        bsnAPIfDot11WEPUndecryptableCount,
        bsnAPIfDot11FailedCount,

--Begin bsnAPIfDot11PhyChannelTable
        bsnAPIfDot11EDThreshold,
        bsnAPIfDot11TIThreshold,

--Begin bsnAPIfProfileThresholdConfigTable
        bsnAPIfProfileParamAssignment,
        bsnAPIfForeignInterferenceThreshold,
        bsnAPIfForeignNoiseThreshold,
        bsnAPIfRFUtilizationThreshold,
        bsnAPIfThroughputThreshold,
        bsnAPIfMobilesThreshold,
        bsnAPIfCoverageThreshold,
        bsnAPIfMobileMinExceptionLevel,
        bsnAPIfCoverageExceptionLevel,

--Begin bsnAPIfLoadParametersTable
        bsnAPIfLoadRxUtilization,
        bsnAPIfLoadTxUtilization,
        bsnAPIfLoadChannelUtilization,
        bsnAPIfLoadNumOfClients,
        bsnAPIfPoorSNRClients,

--Begin bsnAPIfChannelInterfaceInfoTable  
        bsnAPIfInterferenceChannelNo,
        bsnAPIfInterferencePower,
        bsnAPIfInterferenceUtilization,


--Begin bsnAPIfNoiseChannelNo
        bsnAPIfNoiseChannelNo,
        bsnAPIfDBNoisePower,

--Begin bsnAPIfProfileStateTable
        bsnAPIfLoadProfileState,
        bsnAPIfInterferenceProfileState,
        bsnAPIfNoiseProfileState,
        bsnAPIfCoverageProfileState,

--Begin bsnAPIfRxNeighborsTable
        bsnAPIfRxNeighborMacAddress,
        bsnAPIfRxNeighborIpAddress,
        bsnAPIfRxNeighborRSSI,
        bsnAPIfRxNeighborSlot,

--Begin bsnAPIfStationRSSICoverageInfoTable
        bsnAPIfStationRSSICoverageIndex,
        bsnAPIfRSSILevel,
        bsnAPIfStationCountOnRSSI,

--Begin bsnAPIfStationSNRCoverageInfoTable
        bsnAPIfStationSNRCoverageIndex,
        bsnAPIfSNRLevel,
        bsnAPIfStationCountOnSNR,

--Begin bsnAPIfRecommendedRFParametersTable
        bsnAPIfRecommendedChannelNumber,
        bsnAPIfRecommendedTxPowerLevel,
        bsnAPIfRecommendedRTSThreshold,
        bsnAPIfRecommendedFragmentationThreshold,

--Begin bsnAPIfWlanOverrideTable
        bsnAPIfWlanOverrideId,
        bsnAPIfWlanOverrideSsid,
        bsnAPIfWlanOverrideRowStatus,

--Begin bsnMeshNodeTable
        bsnMeshNodeRole,
        bsnMeshNodeGroup,
        bsnMeshNodeBackhaul,
        bsnMeshNodeBackhaulPAP,
        bsnMeshNodeBackhaulRAP,
        bsnMeshNodeDataRate,
        bsnMeshNodeChannel,
        bsnMeshNodeRoutingState,
        bsnMeshNodeMalformedNeighPackets,
        bsnMeshNodePoorNeighSnr,
        bsnMeshNodeBlacklistPackets,
        bsnMeshNodeInsufficientMemory,
        bsnMeshNodeRxNeighReq,
        bsnMeshNodeRxNeighRsp,
        bsnMeshNodeTxNeighReq,
        bsnMeshNodeTxNeighRsp,
        bsnMeshNodeParentChanges,
        bsnMeshNodeNeighTimeout,
        bsnMeshNodeParentMacAddress,
        bsnMeshNodeAPType,
        bsnMeshNodeEthernetBridge,
        bsnMeshNodeHops,
        bsnMeshNeighMacAddress,

--Begin bsnMeshNeighsTable 
        bsnMeshNeighType,
        bsnMeshNeighState,
        bsnMeshNeighSnr,
        bsnMeshNeighSnrUp,
        bsnMeshNeighSnrDown,
        bsnMeshNeighLinkSnr,
        bsnMeshNeighAdjustedEase,
        bsnMeshNeighUnadjustedEase,
        bsnMeshNeighRapEase,
        bsnMeshNeighTxParent,
        bsnMeshNeighRxParent,
        bsnMeshNeighPoorSnr,
        bsnMeshNeighLastUpdate,
        bsnMeshNeighParentChange,

--Begin bsnAPIfRadarChannelStatisticsTable
        bsnAPIfRadarDetectedChannelNumber,
        bsnAPIfRadarSignalLastHeard
    }
    STATUS      current
    DESCRIPTION
        "This collection of objects provide the information
         about Airespace APs that are associated with the Switch.
         These objects are defined under bsnAP object."
    ::= { bsnWrasGroups 2 }

bsnGlobalDot11Group OBJECT-GROUP
    OBJECTS {
-- Begin bsnGlobalDot11Config
        bsnGlobalDot11PrivacyOptionImplemented,
        bsnGlobalDot11AuthenticationResponseTimeOut,
        bsnGlobalDot11MultiDomainCapabilityImplemented,
        bsnGlobalDot11MultiDomainCapabilityEnabled,
        bsnGlobalDot11CountryIndex,
        bsnGlobalDot11LoadBalancing,
        bsnGlobalDot11RogueTimer,
        bsnPrimaryMwarForAPs,
        bsnRtpProtocolPriority,
        bsnSystemCurrentTime,
        bsnUpdateSystemTime,
        bsnOperatingTemperatureEnvironment,
        bsnSensorTemperature,
        bsnTemperatureAlarmLowLimit,
        bsnTemperatureAlarmHighLimit,
        bsnVirtualGatewayAddress,
        bsnRFMobilityDomainName,
        bsnClientWatchListFeature,
        bsnRogueLocationDiscoveryProtocol,
        bsnRogueAutoContainFeature,
        bsnOverAirProvisionApMode,
        bsnMaximumNumberOfConcurrentLogins,
        bsnAutoContainRoguesAdvertisingSsid,
        bsnAutoContainAdhocNetworks,
        bsnAutoContainTrustedClientsOnRogueAps,
        bsnValidateRogueClientsAgainstAAA,
        bsnSystemTimezoneDelta,
        bsnSystemTimezoneDeltaMinutes,
        bsnSystemTimezoneDaylightSavings,
        bsnAllowAuthorizeApAgainstAAA,
        bsnApFallbackEnabled,
        bsnAppleTalkEnabled,

--Begin bsnTrustedApPolicyConfig
        bsnPolicyForMisconfiguredAps,
        bsnEncryptionPolicyEnforced,
        bsnPreamblePolicyEnforced,
        bsnDot11ModePolicyEnforced,
        bsnRadioTypePolicyEnforced,
        bsnValidateSsidForTrustedAp,
        bsnAlertIfTrustedApMissing,
        bsnTrustedApEntryExpirationTimeout,

--Begin bsnClientExclusionPolicyConfig
        bsnExcessive80211AssocFailures,
        bsnExcessive80211AuthFailures,
        bsnExcessive8021xAuthFailures,
        bsnExternalPolicyServerFailures,
        bsnExcessiveWebAuthFailures,
        bsnIPTheftORReuse,

--Begin bsnSignatureConfig
        bsnStandardSignaturePrecedence,
        bsnStandardSignatureName,
        bsnStandardSignatureDescription,
        bsnStandardSignatureFrameType,
        bsnStandardSignatureAction,
        bsnStandardSignatureState,
        bsnStandardSignatureFrequency,
        bsnStandardSignatureQuietTime,
        bsnStandardSignatureVersion,
        bsnStandardSignatureConfigType,
        bsnStandardSignatureEnable,
        bsnStandardSignatureMacInfo,
        bsnStandardSignatureMacFreq,
        bsnStandardSignatureRowStatus,
        bsnStandardSignaturePatternIndex,
        bsnStandardSignaturePatternOffset,
        bsnStandardSignaturePatternString,
        bsnStandardSignaturePatternMask,
        bsnStandardSignaturePatternOffSetStart,
        bsnStandardSignaturePatternRowStatus,
        bsnCustomSignaturePrecedence,
        bsnCustomSignatureName,
        bsnCustomSignatureDescription,
        bsnCustomSignatureFrameType,
        bsnCustomSignatureAction,
        bsnCustomSignatureState,
        bsnCustomSignatureFrequency,
        bsnCustomSignatureQuietTime,
        bsnCustomSignatureVersion,
        bsnCustomSignatureConfigType,
        bsnCustomSignatureEnable,
        bsnCustomSignatureMacInfo,
        bsnCustomSignatureMacFreq,
        bsnCustomSignatureRowStatus,
        bsnCustomSignaturePatternIndex,
        bsnCustomSignaturePatternOffset,
        bsnCustomSignaturePatternString,
        bsnCustomSignaturePatternMask,
        bsnCustomSignaturePatternOffSetStart,
        bsnCustomSignaturePatternRowStatus,
        bsnSignatureCheckState,

--Begin RfidTagConfig
        bsnRfIdTagStatus,
        bsnRfIdTagDataTimeout,
        bsnRfIdTagAutoTimeoutStatus,

--Begin  bsnAPNeighborAuthConfig
        bsnAPNeighborAuthStatus,
        bsnAPNeighborAuthAlarmThreshold,

        bsnRFNetworkName,
        bsnFastSSIDChangeFeature,

--Begin bsnBridgingPolicyConfig
        bsnBridgingZeroTouchConfig,
        bsnBridgingSharedSecretKey,

-- Begin bsnGlobalDot11b
        bsnGlobalDot11bNetworkStatus,
        bsnGlobalDot11bBeaconPeriod,
        bsnGlobalDot11bDynamicChannelAssignment,
        bsnGlobalDot11bCurrentChannel,
        bsnGlobalDot11bDynamicChannelUpdateInterval,
        bsnGlobalDot11bInputsForDCA,
        bsnGlobalDot11bChannelUpdateCmdInvoke,
        bsnGlobalDot11bChannelUpdateCmdStatus,
        bsnGlobalDot11bDynamicTransmitPowerControl,
        bsnGlobalDot11bDynamicTxPowerControlInterval,
        bsnGlobalDot11bCurrentTxPowerLevel,
        bsnGlobalDot11bInputsForDTP,
        bsnGlobalDot11bPowerUpdateCmdInvoke,
        bsnGlobalDot11bPowerUpdateCmdStatus,
        bsnGlobalDot11bDataRate1Mhz,
        bsnGlobalDot11bDataRate2Mhz,
        bsnGlobalDot11bDataRate5AndHalfMhz,
        bsnGlobalDot11bDataRate11Mhz,
        bsnGlobalDot11bShortPreamble,
        bsnGlobalDot11bDot11gSupport,
        bsnGlobalDot11bDataRate6Mhz,
        bsnGlobalDot11bDataRate9Mhz,
        bsnGlobalDot11bDataRate12Mhz,
        bsnGlobalDot11bDataRate18Mhz,
        bsnGlobalDot11bDataRate24Mhz,
        bsnGlobalDot11bDataRate36Mhz,
        bsnGlobalDot11bDataRate48Mhz,
        bsnGlobalDot11bDataRate54Mhz,
        bsnGlobalDot11bPicoCellMode,
        bsnGlobalDot11bFastRoamingMode,
        bsnGlobalDot11bFastRoamingVoipMinRate,
        bsnGlobalDot11bFastRoamingVoipPercentage,
        bsnGlobalDot11b80211eMaxBandwidth,
        bsnGlobalDot11bDTPCSupport,
        bsnGlobalDot11bMediumOccupancyLimit,
        bsnGlobalDot11bCFPPeriod,
        bsnGlobalDot11bCFPMaxDuration,
        bsnGlobalDot11bCFPollable,
        bsnGlobalDot11bCFPollRequest,
        bsnGlobalDot11bDTIMPeriod,
        bsnGlobalDot11bMaximumTransmitPowerLevel,
        bsnGlobalDot11bFirstChannelNumber,
        bsnGlobalDot11bNumberofChannels,
        bsnGlobalDot11bRTSThreshold,
        bsnGlobalDot11bShortRetryLimit,
        bsnGlobalDot11bLongRetryLimit,
        bsnGlobalDot11bFragmentationThreshold,
        bsnGlobalDot11bMaxTransmitMSDULifetime,
        bsnGlobalDot11bMaxReceiveLifetime,
        bsnGlobalDot11bEDThreshold,
        bsnGlobalDot11bChannelAgilityEnabled,
        bsnGlobalDot11bPBCCOptionImplemented,
        bsnGlobalDot11bShortPreambleOptionImplemented,

-- Begin bsnGlobalDot11a
        bsnGlobalDot11aNetworkStatus,
        bsnGlobalDot11aLowBandNetwork,
        bsnGlobalDot11aMediumBandNetwork,
        bsnGlobalDot11aHighBandNetwork,
        bsnGlobalDot11aBeaconPeriod,
        bsnGlobalDot11aDynamicChannelAssignment,
        bsnGlobalDot11aCurrentChannel,
        bsnGlobalDot11aDynamicChannelUpdateInterval,
        bsnGlobalDot11aInputsForDCA,
        bsnGlobalDot11aChannelUpdateCmdInvoke,
        bsnGlobalDot11aChannelUpdateCmdStatus,
        bsnGlobalDot11aDynamicTransmitPowerControl,
        bsnGlobalDot11aCurrentTxPowerLevel,
        bsnGlobalDot11aDynamicTxPowerControlInterval,
        bsnGlobalDot11aInputsForDTP,
        bsnGlobalDot11aPowerUpdateCmdInvoke,
        bsnGlobalDot11aPowerUpdateCmdStatus,
        bsnGlobalDot11aDataRate6Mhz,
        bsnGlobalDot11aDataRate9Mhz,
        bsnGlobalDot11aDataRate12Mhz,
        bsnGlobalDot11aDataRate18Mhz,
        bsnGlobalDot11aDataRate24Mhz,
        bsnGlobalDot11aDataRate36Mhz,
        bsnGlobalDot11aDataRate48Mhz,
        bsnGlobalDot11aDataRate54Mhz,
        bsnGlobalDot11aPicoCellMode,
        bsnGlobalDot11aFastRoamingMode,
        bsnGlobalDot11aFastRoamingVoipMinRate,
        bsnGlobalDot11aFastRoamingVoipPercentage,
        bsnGlobalDot11a80211eMaxBandwidth,
        bsnGlobalDot11aDTPCSupport,
        bsnGlobalDot11aMediumOccupancyLimit,
        bsnGlobalDot11aCFPPeriod,
        bsnGlobalDot11aCFPMaxDuration,
        bsnGlobalDot11aCFPollable,
        bsnGlobalDot11aCFPollRequest,
        bsnGlobalDot11aDTIMPeriod,
        bsnGlobalDot11aMaximumTransmitPowerLevel,
        bsnGlobalDot11aFirstChannelNumber,
        bsnGlobalDot11aNumberofChannels,
        bsnGlobalDot11aRTSThreshold,
        bsnGlobalDot11aShortRetryLimit,
        bsnGlobalDot11aLongRetryLimit,
        bsnGlobalDot11aFragmentationThreshold,
        bsnGlobalDot11aMaxTransmitMSDULifetime,
        bsnGlobalDot11aMaxReceiveLifetime,
        bsnGlobalDot11aTIThreshold,
        bsnGlobalDot11aChannelAgilityEnabled,
-- Begin bsnGlobalDot11a
        bsnGlobalDot11hPowerConstraint,
        bsnGlobalDot11hChannelSwitchEnable,
        bsnGlobalDot11hChannelSwitchMode,
        bsnRrmDot11aGlobalAutomaticGrouping

    }
    STATUS      current
    DESCRIPTION
        "This collection of objects provide the information
         about Airespace 802.11 standard attributes applied globally. 
         These objects are defined under bsnGlobalDot11 object."
    ::= { bsnWrasGroups 3 }

bsnRrmGroup OBJECT-GROUP
    OBJECTS {

--Begin bsnRrmDot11a
        bsnRrmDot11aGroupLeaderMacAddr,
        bsnRrmIsDot11aGroupLeader,
        bsnRrmDot11aGroupLastUpdateTime,
        bsnRrmDot11aGlobalGroupInterval,
        bsnWrasDot11aPeerMacAddress,
        bsnWrasDot11aPeerIpAddress,
        bsnRrmDot11aForeignInterferenceThreshold,
        bsnRrmDot11aForeignNoiseThreshold,
        bsnRrmDot11aRFUtilizationThreshold,
        bsnRrmDot11aThroughputThreshold,
        bsnRrmDot11aMobilesThreshold,
        bsnRrmDot11aCoverageThreshold,
        bsnRrmDot11aMobileMinExceptionLevel,
        bsnRrmDot11aCoverageExceptionLevel,
        bsnRrmDot11aSignalMeasurementInterval,
        bsnRrmDot11aNoiseMeasurementInterval,
        bsnRrmDot11aLoadMeasurementInterval,
        bsnRrmDot11aCoverageMeasurementInterval,
        bsnRrmDot11aChannelMonitorList,
        bsnRrmDot11aSetFactoryDefault,

--Begin bsnRrmDot11b
        bsnRrmDot11bGlobalAutomaticGrouping,
        bsnRrmDot11bGroupLeaderMacAddr,
        bsnRrmIsDot11bGroupLeader,
        bsnRrmDot11bGroupLastUpdateTime,
        bsnRrmDot11bGlobalGroupInterval,
        bsnWrasDot11bPeerMacAddress,
        bsnWrasDot11bPeerIpAddress,
        bsnRrmDot11bForeignInterferenceThreshold,
        bsnRrmDot11bForeignNoiseThreshold,
        bsnRrmDot11bRFUtilizationThreshold,
        bsnRrmDot11bThroughputThreshold,
        bsnRrmDot11bMobilesThreshold,
        bsnRrmDot11bCoverageThreshold,
        bsnRrmDot11bMobileMinExceptionLevel,
        bsnRrmDot11bCoverageExceptionLevel,
        bsnRrmDot11bSignalMeasurementInterval,
        bsnRrmDot11bNoiseMeasurementInterval,
        bsnRrmDot11bLoadMeasurementInterval,
        bsnRrmDot11bCoverageMeasurementInterval,
        bsnRrmDot11bChannelMonitorList,
        bsnRrmDot11bSetFactoryDefault
    }
    STATUS      current
    DESCRIPTION
        "This collection of objects provide the information
         about Airespace Radio Resource Management Configuration 
         Parameters. These objects are defined under bsnRrm object."
    ::= { bsnWrasGroups 4 }

bsnAAAGroup OBJECT-GROUP
    OBJECTS {
-- Begin bsnRadiusAuthServerTable
        bsnRadiusAuthServerIndex,
        bsnRadiusAuthServerAddress,
        bsnRadiusAuthClientServerPortNumber,
        bsnRadiusAuthServerKey,
        bsnRadiusAuthServerStatus,
        bsnRadiusAuthServerKeyFormat,
        bsnRadiusAuthServerRFC3576,
        bsnRadiusAuthServerIPSec,
        bsnRadiusAuthServerIPSecAuth,
        bsnRadiusAuthServerIPSecEncryption,
        bsnRadiusAuthServerIPSecIKEPhase1,
        bsnRadiusAuthServerIPSecIKELifetime,
        bsnRadiusAuthServerIPSecDHGroup,
        bsnRadiusAuthServerNetworkUserConfig,
        bsnRadiusAuthServerMgmtUserConfig,
        bsnRadiusAuthServerRetransmitTimeout,
        bsnRadiusAuthServerKeyWrapKEKkey,
        bsnRadiusAuthServerKeyWrapMACKkey,
        bsnRadiusAuthServerKeyWrapFormat,
        bsnRadiusAuthServerRowStatus,

-- Begin bsnRadiusAccServerTable
        bsnRadiusAccServerIndex,
        bsnRadiusAccServerAddress,
        bsnRadiusAccClientServerPortNumber,
        bsnRadiusAccServerKey,
        bsnRadiusAccServerStatus,
        bsnRadiusAccServerKeyFormat,
        bsnRadiusAccServerIPSec,
        bsnRadiusAccServerIPSecAuth,
        bsnRadiusAccServerIPSecEncryption,
        bsnRadiusAccServerIPSecIKEPhase1,
        bsnRadiusAccServerIPSecIKELifetime,
        bsnRadiusAccServerIPSecDHGroup,
        bsnRadiusAccServerNetworkUserConfig,
        bsnRadiusAccServerRetransmitTimeout,
        bsnRadiusAccServerRowStatus,

-- Begin bsnRadiusAuthServerStatsTable
        bsnRadiusAuthClientRoundTripTime,
        bsnRadiusAuthClientAccessRequests,
        bsnRadiusAuthClientAccessRetransmissions,
        bsnRadiusAuthClientAccessAccepts,
        bsnRadiusAuthClientAccessRejects,
        bsnRadiusAuthClientAccessChallenges,
        bsnRadiusAuthClientMalformedAccessResponses,
        bsnRadiusAuthClientBadAuthenticators,
        bsnRadiusAuthClientPendingRequests,
        bsnRadiusAuthClientTimeouts,
        bsnRadiusAuthClientUnknownTypes,
        bsnRadiusAuthClientPacketsDropped,

-- Begin bsnRadiusAccServerStatsTable
        bsnRadiusAccClientRoundTripTime,
        bsnRadiusAccClientRequests,
        bsnRadiusAccClientRetransmissions,
        bsnRadiusAccClientResponses,
        bsnRadiusAccClientMalformedResponses,
        bsnRadiusAccClientBadAuthenticators,
        bsnRadiusAccClientPendingRequests,
        bsnRadiusAccClientTimeouts,
        bsnRadiusAccClientUnknownTypes,
        bsnRadiusAccClientPacketsDropped,


--Begin bsnAclTable
        bsnAclName,
        bsnAclApplyMode,
        bsnAclRowStatus,

--Begin bsnAclRuleTable
        bsnAclRuleIndex,
        bsnAclRuleAction,
        bsnAclRuleDirection,
        bsnAclRuleSourceIpAddress,
        bsnAclRuleSourceIpNetmask,
        bsnAclRuleDestinationIpAddress,
        bsnAclRuleDestinationIpNetmask,
        bsnAclRuleProtocol,
        bsnAclRuleStartSourcePort,
        bsnAclRuleEndSourcePort,
        bsnAclRuleStartDestinationPort,
        bsnAclRuleEndDestinationPort,
        bsnAclRuleDscp,
        bsnAclNewRuleIndex,
        bsnAclRuleRowStatus,

--Begin bsnMacFilterTable
        bsnMacFilterAddress,
        bsnMacFilterWlanId,
        bsnMacFilterInterfaceName,
        bsnMacFilterDescription,
        bsnMacFilterRowStatus,

--Begin bsnLocalNetUserTable
        bsnLocalNetUserName,
        bsnLocalNetUserWlanId,
        bsnLocalNetUserPassword,
        bsnLocalNetUserDescription,
        bsnLocalNetUserLifetime,
        bsnLocalNetUserStartTime,
        bsnLocalNetUserRemainingTime,
        bsnLocalNetUserRowStatus,

--Begin bsnLocalManagementUserTable
        bsnLocalManagementUserName,
        bsnLocalManagementUserPassword,
        bsnLocalManagementUserAccessMode,
        bsnLocalManagementUserRowStatus,

--Begin bsnBlackListClientTable
        bsnBlackListClientMacAddress,
        bsnBlackListClientDescription,
        bsnBlackListClientRowStatus,

        bsnRadiusAuthKeyWrapEnable,
        bsnRadiusAuthCacheCredentialsLocally,
        bsnAAAMacDelimiter,
        bsnAAARadiusCompatibilityMode,
        bsnAAARadiusCallStationIdType,
        bsnAAALocalDatabaseSize,
        bsnAAACurrentLocalDatabaseSize,

--Begin bsnExternalPolicyServerTable
        bsnExternalPolicyServerAclName,

        bsnAcceptSelfSignedCertificate,
        bsnSystemClockTime,

--Begin bsnAPAuthorizationTable
        bsnAPAuthMacAddress,
        bsnAPAuthCertificateType,
        bsnAPAuthHashKey,
        bsnAPAuthRowStatus
    }
    STATUS      current
    DESCRIPTION
        "This collection of objects provide the information
         about Airespace Authentication, Authorization, and 
         Accounting Attributes. These objects are defined under
         bsnAAA object."
    ::= { bsnWrasGroups 5 }


bsnTrapsGroup OBJECT-GROUP
    OBJECTS {
-- Begin bsnTrapControl
        bsnDot11StationTrapControlMask,
        bsnAPTrapControlMask,
        bsnAPProfileTrapControlMask,
        bsnAPMacAddrTrapVariable,
        bsnAPNameTrapVariable,
        bsnAPSlotIdTrapVariable,
        bsnAPChannelNumberTrapVariable,
        bsnAPCoverageThresholdTrapVariable,
        bsnAPCoverageFailedClients,
        bsnAPCoverageTotalClients,
        bsnClientMacAddr,
        bsnClientRssi,
        bsnClientSnr,
        bsnInterferenceEnergyBeforeChannelUpdate,
        bsnInterferenceEnergyAfterChannelUpdate,
        bsnAPPortNumberTrapVariable,
        bsnAPParamUpdateTrapControlMask,
        bsnConfigSaveTrapEnable,
        bsnRADIUSServerTrapEnable,
        bsnAuthenticationFailureTrapEnable,
        bsn80211SecurityTrapControlMask,
        bsnWpsTrapControlEnable,

--Begin bsnTrapVariable
        bsnAuthFailureUserName,
        bsnAuthFailureUserType,
        bsnRemoteIPv4Address,
        bsnIpsecErrorCount,
        bsnIpsecSPI,
        bsnRemoteUdpPort,
        bsnIkeAuthMethod,
        bsnIkeTotalInitFailures,
        bsnIkeTotalInitNoResponses,
        bsnIkeTotalRespFailures,
        bsnNotifiesSent,
        bsnNotifiesReceived,
        bsnSuiteInitFailures,
        bsnSuiteRespondFailures,
        bsnInitiatorCookie,
        bsnResponderCookie,
        bsnIsakmpInvalidCookies,
        bsnIpsecTrapsMask,
        bsnRogueAPTrapEnable,
        bsnCurrentRadiosCount,
        bsnLicenseRadioCount,
        bsnMaxRogueCount,
        bsnStationMacAddress,
        bsnStationAPMacAddr,
        bsnStationAPIfSlotId,
        bsnUserIpAddress,
        bsnStationReasonCode,
        bsnStationBlacklistingReasonCode,
        bsnStationUserName,
        bsnRogueAPOnWiredNetwork,
        bsnRogueAdhocMode,
        bsnDuplicateIpReportedByAP,
        bsnDuplicateIpTrapVariable,
        bsnDuplicateIpTrapClear,
        bsnNavDosAttackSourceMacAddr,
        bsnWlanIdTrapVariable,
        bsnClearTrapVariable,
        bsnTrustedApEncryptionUsed,
        bsnTrustedApEncryptionRequired,
        bsnTrustedApRadioPolicyUsed,
        bsnNetworkType,
        bsnNetworkState,
        bsnSignatureType,
        bsnSignatureName,
        bsnSignatureDescription,
        bsnSignatureAttackPreced,
        bsnSignatureAttackFrequency,
        bsnSignatureAttackChannel,
        bsnSignatureAttackerMacAddress,
        bsnApRegulatoryDomain,
        bsnImpersonatedAPMacAddr,
        bsnTrustedApPreambleUsed,
        bsnTrustedApPreambleRequired,
        bsnTrustedApRadioPolicyRequired,
        bsnGroupDirectoryMemberIPAddress,
        bsnGroupDirectoryMemberMacAddress,
        bsnGroupDirectoryDicoveryType,
        bsnMemberCurrentAnchoredClients,
        bsnMemberTotalAnchoredClients,
        bsnMemberCurrentExportedClients,
        bsnMemberTotalExportedClients,
        bsnMemberCurrentImportedClients,
        bsnMemberTotalImportedClients,
        bsnMemberTotalHandoffErrors,
        bsnMemberTotalCommunicationErrors,
        bsnAPGroupsVlanFeature,
        bsnAPGroupsVlanName,
        bsnAPGroupsVlanDescription,
        bsnAPGroupsVlanRowStatus,
        bsnAPGroupsVlanMappingSsid,
        bsnAPGroupsVlanMappingInterfaceName,
        bsnAPGroupsVlanMappingRowStatus,
        bsnLicenseKeyTrapVariable,
        bsnApFunctionalityDisableReasonCode,
        bsnLicenseKeyFeatureSetTrapVariable,
        bsnAPAuthorizationFailureCause,
        bsnAPIfUpDownCause,
        bsnAPInvalidRadioType,
        locationNotifyContent,
        bsnSignatureMacInfo
    }
    STATUS      current
    DESCRIPTION
        "This collection of objects provide the information
         about Airespace Trap Configuration and Trap definition.
         These objects are defined under bsnTrap."
    ::= { bsnWrasGroups 6 }


bsnUtilityGroup OBJECT-GROUP
    OBJECTS {
-- bsnUtility
        bsnSyslogEnable,
        bsnSyslogRemoteAddress,
--Begin bsnPingTestTable
        bsnPingTestId,
        bsnPingTestIPAddress,
        bsnPingTestSendCount,
        bsnPingTestReceivedCount,
        bsnPingTestStatus,
        bsnPingTestRowStatus
    }
    STATUS      current
    DESCRIPTION
        "This collection of objects provide the information
         about Airespace General Utilities such as ping, syslog.
         These objects are defined under bsnUtility."
    ::= { bsnWrasGroups 7 }

bsnMobilityGroup OBJECT-GROUP
    OBJECTS {
--Begin bsnMobiltyConfig
        bsnMobilityProtocolPortNum,
        bsnMobilityDynamicDiscovery,
        bsnMobilityStatsReset,

--Begin bsnMobilityGroupMembersTable
        bsnMobilityGroupMemberMacAddress,
        bsnMobilityGroupMemberIPAddress,
        bsnMobilityGroupMemberGroupName,
        bsnMobilityGroupMemberRowStatus,
 
--Begin bsnMobilityAnchorsTable
        bsnMobilityAnchorWlanSsid,
        bsnMobilityAnchorSwitchIPAddress,
        bsnMobilityAnchorRowStatus,

--Begin bsnMobiltyStats
        bsnTotalHandoffRequests,
        bsnTotalHandoffs,
        bsnCurrentExportedClients,
        bsnTotalExportedClients,
        bsnCurrentImportedClients,
        bsnTotalImportedClients,
        bsnTotalHandoffErrors,
        bsnTotalCommunicationErrors,
        bsnTotalReceiveErrors,
        bsnTotalTransmitErrors,
        bsnTotalResponsesRetransmitted,
        bsnTotalHandoffEndRequestsReceived,
        bsnTotalStateTransitionsDisallowed,
        bsnTotalResourceErrors,
        bsnTotalHandoffRequestsSent,
        bsnTotalHandoffRepliesReceived,
        bsnTotalHandoffAsLocalReceived,
        bsnTotalHandoffAsForeignReceived,
        bsnTotalHandoffDeniesReceived,
        bsnTotalAnchorRequestsSent,
        bsnTotalAnchorDenyReceived,
        bsnTotalAnchorGrantReceived,
        bsnTotalAnchorTransferReceived,
        bsnTotalHandoffRequestsIgnored,
        bsnTotalPingPongHandoffRequestsDropped,
        bsnTotalHandoffRequestsDropped,
        bsnTotalHandoffRequestsDenied,
        bsnTotalClientHandoffAsLocal,
        bsnTotalClientHandoffAsForeign,
        bsnTotalAnchorRequestsReceived,
        bsnTotalAnchorRequestsDenied,
        bsnTotalAnchorRequestsGranted,
        bsnTotalAnchorTransferred,
        bsnTotalHandoffRequestsReceived
    }
    STATUS      current
    DESCRIPTION
        "This collection of objects provide the information
         about Airespace Mobility Group Parameters and ststistics.
         These are objects defined under bsnMobility."
    ::= { bsnWrasGroups 8 }

bsnIpsecGroup OBJECT-GROUP
    OBJECTS {
-- Begin bsnGlobalDot11Config
        bsnWrasIpsecCACertificate,
        bsnWrasIpsecCACertificateUpdate,

--Begin bsnWrasIpsecCertTable
        bsnWrasIpsecCertName,
        bsnWrasIpsecCertificateUpdate,
        bsnWrasIpsecCertificate,
        bsnWrasIpsecCertPassword,
        bsnWrasIpsecCertStatus
    }
    STATUS      current
    DESCRIPTION
        "This collection of objects provide the information
         about Airespace Global IpSec Group. These objects are defined
         under bsnIpsec."
    ::= { bsnWrasGroups 9 }




bsnWrasDepGroup OBJECT-GROUP
    OBJECTS {
--Begin bsnDot11EssTable
        bsnDot11EssWPASecurity,
        bsnDot11EssWPAEncryptionType,
        bsnDot11EssWPAAuthKeyMgmtMode,
        bsnDot11EssWPAAuthPresharedKey,
        bsnDot11EssWPAAuthPresharedKeyHex,
        bsnDot11EssRSNSecurity,
        bsnDot11EssRSNWPACompatibilityMode,
        bsnDot11EssRSNAllowTKIPClients,
        bsnDot11EssRSNAuthKeyMgmtMode,
        bsnDot11EssRSNAuthPresharedKey,
        bsnDot11EssRSNAuthPresharedKeyHex,

--Begin bsnAPIfDot11PhyTxPowerTable
        bsnAPIfDot11NumberSupportedPowerLevels,
        bsnAPIfDot11TxPowerLevel1,
        bsnAPIfDot11TxPowerLevel2,
        bsnAPIfDot11TxPowerLevel3,
        bsnAPIfDot11TxPowerLevel4,
        bsnAPIfDot11TxPowerLevel5,
        bsnAPIfDot11TxPowerLevel6,
        bsnAPIfDot11TxPowerLevel7,
        bsnAPIfDot11TxPowerLevel8,

--Begin bsnAPIfDot11PhyChannelTable
        bsnAPIfDot11CurrentCCAMode,

--Begin bsnLinkTestTable
        bsnLinkTestId,
        bsnLinkTestMacAddress,
        bsnLinkTestSendPktCount,
        bsnLinkTestSendPktLength,
        bsnLinkTestReceivedPktCount,
        bsnLinkTestClientRSSI,
        bsnLinkTestLocalSNR,
        bsnLinkTestLocalRSSI,
        bsnLinkTestStatus,
        bsnLinkTestRowStatus
    }
    STATUS      deprecated
    DESCRIPTION
        "This collection of objects are  derprecated in bsnWireless 
         module."
    ::= { bsnWrasGroups 10 }

bsnWrasObsGroup OBJECT-GROUP
    OBJECTS {
--Begin bsnUsersTable
        bsnUserName,
        bsnUserPassword,
        bsnUserEssIndex,
        bsnUserAccessMode,
        bsnUserType,
        bsnUserInterfaceName,
        bsnUserRowStatus,

--Begin bsnExternalPolicyServerTable
        bsnExternalPolicyServerIndex,
        bsnExternalPolicyServerAddress,
        bsnExternalPolicyServerPortNumber,
        bsnExternalPolicyServerKey,
        bsnExternalPolicyServerAdminStatus,
        bsnExternalPolicyServerConnectionStatus,
        bsnExternalPolicyServerRowStatus,

--Begin bsnThirdPartAPEntry 
        bsnThirdPartyAPMacAddress,
        bsnThirdPartyAPInterface,
        bsnThirdPartyAPIpAddress,
        bsnThirdPartyAP802Dot1XRequired,
        bsnThirdPartyAPMirrorMode,
        bsnThirdPartyAPRowStatus,

--Begin  bsnWatchListClientEntry 
        bsnWatchListClientKey,
        bsnWatchListClientType,
        bsnWatchListClientRowStatus
    }
    STATUS      obsolete
    DESCRIPTION
        "This collection of objects are  obsoleted in bsnWireless 
         module."
    ::= { bsnWrasGroups 11 }

bsnWrasTrap NOTIFICATION-GROUP
    NOTIFICATIONS {
        bsnDot11StationDisassociate,
        bsnDot11StationDeauthenticate,
        bsnDot11StationAuthenticateFail,
        bsnDot11StationAssociateFail,
        bsnDot11StationBlacklisted,
        bsnDot11StationAssociate,
        bsnAPUp,
        bsnAPDown,
        bsnAPAssociated,
        bsnAPDisassociated,
        bsnAPIfUp,
        bsnAPIfDown,
        bsnAPLoadProfileFailed,
        bsnAPNoiseProfileFailed,
        bsnAPInterferenceProfileFailed,
        bsnAPCoverageProfileFailed,
        bsnAPLoadProfileUpdatedToPass,
        bsnAPNoiseProfileUpdatedToPass,
        bsnAPInterferenceProfileUpdatedToPass,
        bsnAPCoverageProfileUpdatedToPass,
        bsnAPCurrentTxPowerChanged,
        bsnAPCurrentChannelChanged,
        bsnRrmDot11aGroupingDone,
        bsnRrmDot11bGroupingDone,
        bsnConfigSaved,
        bsnDot11EssCreated,
        bsnDot11EssDeleted,
        bsnRADIUSServerNotResponding,
        bsnAuthenticationFailure,
        bsnIpsecEspAuthFailureTrap,
        bsnIpsecEspReplayFailureTrap,
        bsnIpsecEspInvalidSpiTrap,
        bsnIpsecIkeNegFailure,
        bsnIpsecSuiteNegFailure,
        bsnIpsecInvalidCookieTrap,
        bsnRogueAPDetected,
        bsnRogueAPRemoved,
        bsnRogueAPDetectedOnWiredNetwork,
        bsnApHasNoRadioCards,
        bsnDuplicateIpAddressReported,
        bsnAPContainedAsARogue,
        bsnNetworkStateChanged,
        bsnSignatureAttackDetected,
        bsnAPRadioCardTxFailure,
        bsnAPRadioCardTxFailureClear,
        bsnAPRadioCardRxFailure,
        bsnAPRadioCardRxFailureClear,
        bsnAPImpersonationDetected,
        bsnAPRegulatoryDomainMismatch,
        bsnTrustedApHasInvalidPreamble,
        bsnRadiosExceedLicenseCount,
        bsnSensedTemperatureTooHigh,
        bsnSensedTemperatureTooLow,
        bsnTemperatureSensorFailure,
        bsnTemperatureSensorClear,
        bsnPOEControllerFailure,
        bsnMaxRogueCountExceeded,
        bsnMaxRogueCountClear,
        bsnApMaxRogueCountExceeded,
        bsnApMaxRogueCountClear,
        bsnApBigNavDosAttack,
        bsnTooManyUnsuccessLoginAttempts,
        bsnWepKeyDecryptError,
        bsnWpaMicErrorCounterActivated,
        bsnAdhocRogueAutoContained,
        bsnRogueApAutoContained,
        bsnTrustedApHasInvalidEncryption,
        bsnTrustedApHasInvalidRadioPolicy,
        bsnTrustedApHasInvalidSsid,
        bsnTrustedApIsMissing,
        bsnAPIPAddressFallback,
        bsnAPFunctionalityDisabled,
        bsnRxMulticastQueueFull,
        bsnRadarChannelDetected,
        bsnRadarChannelCleared,
        bsnAPAuthorizationFailure,
        radioCoreDumpTrap,
        invalidRadioTrap,
        countryChangeTrap,
        unsupportedAPTrap,
        heartbeatLossTrap,
        locationNotifyTrap
    }
    STATUS      current
    DESCRIPTION
        "This  collection of objects provides all notification 
         that Switch need to generate to the Management System." 
    ::= { bsnWrasGroups 12 }

--********************************************************************
--*   End of units of conformance
--********************************************************************

-- ************************************************************
-- *   End of Airespace Wirelss MIB
-- ************************************************************

END
