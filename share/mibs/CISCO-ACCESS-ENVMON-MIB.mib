-- *****************************************************************
-- CISCO-ACCESS-ENVMON-MIB.my: CISCO ACCESS ENVMON MIB file
--
-- November 1996  Hongchi Shih
--
-- Copyright (c) 1996, 1997, 1998 by cisco Systems, Inc.
-- All rights reserved.
-- *****************************************************************

CISCO-ACCESS-ENVMON-MIB  DEFINITIONS ::= BEGIN

IMPORTS
        MODULE-IDENTITY,
        OBJECT-TYPE,
        NOTIFICATION-TYPE 
                FROM SNMPv2-SMI
        MODULE-COMPLIANCE,
        OBJECT-GROUP
                FROM SNMPv2-CONF
        ciscoEnvMonSupplyStatusEntry,
        ciscoEnvMonTemperatureStatusDescr,
        ciscoEnvMonTemperatureState,
        ciscoEnvMonVoltageStatusDescr,
        ciscoEnvMonVoltageState
                FROM CISCO-ENVMON-MIB
        ciscoMgmt
                FROM CISCO-SMI;
 
 
ciscoAccessEnvMonMIB MODULE-IDENTITY
        LAST-UPDATED    "9808050000Z"
        ORGANIZATION    "Cisco Systems, Inc."
        CONTACT-INFO
                "       Cisco Systems
                        Customer Service

                Postal: 170 W. Tasman Drive
                        San Jose, CA  95134
                        USA
 
                Tel: +1 800 553-NETS
 
                E-mail: cs-snmp@cisco.com"
        DESCRIPTION
                "The MIB module to describe the additional status of
                 the Environmental Monitor on those Cisco Access devices
                 which support one.
                "
 	REVISION	"9808050000Z"
 	DESCRIPTION
                "Rename the enumerated values for caemSupplyFailedComponent 
                 and add fan, overvoltage failure events to it. 
                 Add caemVoltageNotification.
                "
        ::= { ciscoMgmt 61 }



-- Cisco Access Environmental Monitor MIB objects definitions

caemObjects    OBJECT IDENTIFIER ::= { ciscoAccessEnvMonMIB 1 }

--
-- Cisco Access Environmental Monitor power supply table 
-- This table augments the ciscoEnvMonSupplyStatusTable defined in
-- CISCO-ENVMON-MIB.
--
caemSupplyStatusTable OBJECT-TYPE
        SYNTAX      SEQUENCE OF CaemSupplyStatusEntry
        MAX-ACCESS  not-accessible
        STATUS      current
        DESCRIPTION
            "The table contains the additional power supply information
             that are not covered in the ciscoEnvMonSupplyStatusTable of
             CISCO-ENVMON-MIB.                                
            "
       ::= { caemObjects 1 }

caemSupplyStatusEntry OBJECT-TYPE
        SYNTAX      CaemSupplyStatusEntry
        MAX-ACCESS  not-accessible
        STATUS      current
        DESCRIPTION
            "Additional information about the failure component or location
             in the power Supply beyond that provided by Cisco Environmental
             Monitor MIB's ciscoEnvMonSupplyStatusEntry.
            "
        AUGMENTS    { ciscoEnvMonSupplyStatusEntry }
      ::= { caemSupplyStatusTable 1 }

CaemSupplyStatusEntry ::=
        SEQUENCE {
            caemSupplyFailedComponent     INTEGER
        }

caemSupplyFailedComponent OBJECT-TYPE
    SYNTAX     INTEGER {
            none            (1),
            inputVoltage    (2),
            dcOutputVoltage (3),
            thermal         (4),
            multiple        (5),
            fan             (6),
            overvoltage     (7)
    }
    MAX-ACCESS read-only
    STATUS     current
    DESCRIPTION
        "The failure component of the power supply being instrumented.
         none            - No failure.
         inputVoltage    - Input power lost in one of the power supplies
         dcOutputVoltage - DC output voltage lost in one of the power supplies
         thermal         - Power supply thermal failure.
         multiple        - Multiple failures.
         fan             - Fan failure
         overvoltage     - Over voltage.
        "
    ::= { caemSupplyStatusEntry 1 }

--****************************************************************************
-- Notifications
--****************************************************************************

caemMIBNotificationPrefix
        OBJECT IDENTIFIER ::= { ciscoAccessEnvMonMIB 2 }
caemMIBNotifications
        OBJECT IDENTIFIER ::= { caemMIBNotificationPrefix 0 }


caemTemperatureNotification NOTIFICATION-TYPE
    OBJECTS {
        ciscoEnvMonTemperatureStatusDescr,
        ciscoEnvMonTemperatureState
        }
    STATUS  current
    DESCRIPTION
        "A caemTemperatureNotification is sent if the over temperature
         condition is detected in the managed system.
         This is a replacement for the ciscoEnvMonTemperatureNotification 
         trap because the information 'ciscoEnvMonTemperatureStatusValue' 
         required by the trap is not available in the managed system.
        "
    ::= { caemMIBNotifications 1 }


caemVoltageNotification NOTIFICATION-TYPE
    OBJECTS	{
	ciscoEnvMonVoltageStatusDescr,
	ciscoEnvMonVoltageState
	}
    STATUS	current
    DESCRIPTION
        "A caemVoltageNotification is sent if the over voltage 
         condition is detected and ciscoEnvMonVoltageState is not set
         to 'notPresent' in the managed system.
         This is a replacement for the ciscoEnvMonVoltageNotification 
         trap because the information 'ciscoEnvMonVoltageStatusValue' 
         required by the trap is not available in the managed system.
        "
	::= { caemMIBNotifications 2 }


caemConformance OBJECT IDENTIFIER ::=
                                { ciscoAccessEnvMonMIB 3 }
caemCompliances OBJECT IDENTIFIER ::=
                                { caemConformance 1 }
caemGroups      OBJECT IDENTIFIER ::=
                                { caemConformance 2 }

-- compliance statements

caemCompliance MODULE-COMPLIANCE
        STATUS      current
        DESCRIPTION
            "The compliance statement for entities which implement
             the Cisco Environmental Monitor Supplemental MIB."
        MODULE      -- this module
        MANDATORY-GROUPS
            { caemGroup }
        ::= { caemCompliances 1 }

-- units of conformance


caemGroup OBJECT-GROUP
        OBJECTS {
            caemSupplyFailedComponent
        }
        STATUS      current
        DESCRIPTION
            "A collection of objects providing the additional Environmental
             Monitor information beyond that provided by
             Cisco Environmental Monitor MIB.
            "
        ::= { caemGroups 1 }

END
