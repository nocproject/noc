-- *****************************************************************
-- CISCO-STP-EXTENSIONS-MIB 
--
-- August 1997, Fei Xu 
--
-- Copyright (c) 1997, 1998-2004 by Cisco Systems, Inc.
-- All rights reserved.
-- *****************************************************************
CISCO-STP-EXTENSIONS-MIB DEFINITIONS ::= BEGIN

IMPORTS
        MODULE-IDENTITY, 
        OBJECT-TYPE, 
        Counter32,
        Integer32, 
        Unsigned32,
        NOTIFICATION-TYPE             
                           FROM SNMPv2-SMI

        MODULE-COMPLIANCE, 
        OBJECT-GROUP,
        NOTIFICATION-GROUP                       
                           FROM SNMPv2-CONF
        TruthValue, 
        TimeStamp, 
        DisplayString,
        RowStatus                              
                           FROM SNMPv2-TC

        vlanTrunkPortEntry, 
        VlanIndex,  
        vtpVlanEntry, 
        vtpVlanEditEntry         
                           FROM CISCO-VTP-MIB

        dot1dStpPortEntry                        
                           FROM BRIDGE-MIB

        ciscoMgmt                                
                           FROM CISCO-SMI;

ciscoStpExtensionsMIB MODULE-IDENTITY
    LAST-UPDATED    "200404080000Z" 
    ORGANIZATION    "Cisco Systems, Inc."
    CONTACT-INFO
            "       Cisco Systems
                    Customer Service

            Postal: 170 W Tasman Drive
                    San Jose, CA  95134
                    USA

               Tel: +1 800 553-NETS

            E-mail: cs-wbu@cisco.com"
    DESCRIPTION
            "The MIB module for managing Cisco extensions to
            the 802.1D Spanning Tree Protocol (STP)."
    REVISION        "200404080000Z"
    DESCRIPTION
            "Added stpxSMSTInstanceCISTGroup.
            Added 3 new bit values into the BITS syntax
            of stpxNotificationEnable: 
            inconsistency(2), rootInconsistency(3), 
            and loopInconsistency(4)."
    REVISION        "200401140000Z"
    DESCRIPTION
            "Deprecated stpxMSTGroup2 and 
            stpxPreferredMSTInstancesGroup.
            Added stpxMSTGroup3, stpxSMSTGroup, 
            stpxSMSTInstanceGroup, stpxSMSTInstanceEditGroup,
            stpxSMSTPortStatusGroup, stpxSMSTPortHelloTimeGroup. 
            Added one new value master(7) to stpxMSTPortRoleValue
            and stpxRSTPPortRoleValue. Added 2 new unused bit 
            value into the BITS syntax of stpxRPVSTPortStatus." 
    REVISION        "200310230000Z"
    DESCRIPTION 
            "Added stpxExtendedSysIDGroup,  
            stpxNotificationEnableGroup, and 
            stpxFastStartOperModeGroup."
    REVISION        "200207110000Z"
    DESCRIPTION 
            "Added Rapid Spanning Tree Protocol support.
            Added stpxUplinkFastOperEnabled and
            stpxBackboneFastOperEnabled objects.
            Replaced stpxMSTPortAdminLinkType, 
            stpxMSTPortOperLinkType, 
            stpxMSTPortProtocolMigration 
            with stpxRSTPPortAdminLinkType,
            stpxRSTPPortOperLinkType and 
            stpxRSTPPortProtocolMigration
            defined in stpxRSTPPortTable.
            Replaced stpxMSTPortRoleTable with
            stpxRSTPPortRoleTable. Added stpxRPVSTPortTable."
    REVISION        "200112060000Z"
    DESCRIPTION 
            "Added per port Bpdu Guard and Bpdu Filter 
            mode configuration support. Modified the
            description of stpxUplinkFastEnabled and
            stpxUplinkStationLearningGenRate for MST
            support. " 
    REVISION        "200109140000Z"
    DESCRIPTION
            "Added MST support, Loop Guard Global Default mode
            support and Fast Start Global Default mode support.
            Deprecated stpxFastStartPortEnable and 
            stpxLoopGuardConfigEnabled objects. Changed description
            of stpxUplinkFastEnabled, stpxUplinkFastTransitions,
            stpxUplinkStationLearningGenRate, 
            stpxUplinkStationLearningFrames objects for MST support." 
    REVISION        "200106200000Z"
    DESCRIPTION
            "Added BPDU Skewing feature support and modified
            the SYNTAX clause of stpxUplinkStationLearningGenRate."
    REVISION        "200104120000Z"
    DESCRIPTION
            "Added PVST+ VLAN Configuration, MISTP to VLAN mapping,
            Loopguard, and Port Fast Start support."
    REVISION        "200005230000Z"
    DESCRIPTION
            "Added Long Spanning Tree Path Cost Mode support."
    REVISION        "200003210000Z"
    DESCRIPTION
            "Added Rootguard, 4k VLAN and MISTP support."
    REVISION        "9711101200Z"
    DESCRIPTION
            "Additional objects to support SSTP."
    REVISION        "9708191200Z"
    DESCRIPTION
            "Initial version of this MIB module."
    ::= { ciscoMgmt 82 }


stpxObjects           OBJECT IDENTIFIER ::= { ciscoStpExtensionsMIB 1 }
stpxUplinkFastObjects OBJECT IDENTIFIER ::= { stpxObjects 1 }
stpxVlanObjects       OBJECT IDENTIFIER ::= { stpxObjects 2 }
stpxInconsistencyObjects
                      OBJECT IDENTIFIER ::= { stpxObjects 3 }

stpxBackboneFastObjects
                      OBJECT IDENTIFIER ::= { stpxObjects 4 }

stpxRootGuardObjects OBJECT IDENTIFIER ::= { stpxObjects 5 }

stpxSpanningTreeObjects  OBJECT IDENTIFIER ::=  { stpxObjects 6 }

stpxMISTPObjects  OBJECT IDENTIFIER ::=  { stpxObjects 7 }

stpxLoopGuardObjects OBJECT IDENTIFIER ::= { stpxObjects 8 }

stpxFastStartObjects OBJECT IDENTIFIER ::= { stpxObjects 9 }

stpxBpduSkewingObjects OBJECT IDENTIFIER ::= { stpxObjects 10 }

stpxMSTObjects OBJECT IDENTIFIER ::= { stpxObjects 11 }

stpxRSTPObjects OBJECT IDENTIFIER ::= { stpxObjects 12 }

stpxRPVSTObjects OBJECT IDENTIFIER ::= { stpxObjects 13 }

stpxSMSTObjects OBJECT IDENTIFIER ::= { stpxObjects 14 }

stpxNotifications     OBJECT IDENTIFIER ::= { ciscoStpExtensionsMIB 2 }

--
--  UplinkFast capability
--

stpxUplinkFastEnabled OBJECT-TYPE
    SYNTAX     TruthValue
    MAX-ACCESS read-write
    STATUS     current
    DESCRIPTION
            "An indication of whether the UplinkFast capability is
             administratively enabled on the device.
 
             If the platform does not support configuration of this
             object when the object value of stpxSpanningTreeType is 
             mst(4), then this object is not instantiated." 
    ::= { stpxUplinkFastObjects 1 }

stpxUplinkFastTransitions OBJECT-TYPE
    SYNTAX     Counter32
    UNITS      "transitions"
    MAX-ACCESS read-only
    STATUS     current
    DESCRIPTION
            "The cumulative number of UplinkFast transitions (from
            the STP 'Blocking' state directly to the STP 'Forwarding'
            state).  All transitions are included in this counter,
            irrespective of the instance of the Spanning Tree 
            Protocol on which they occur.

            If the platform supports the stpxUplinkFastOperEnabled 
            object, then this object is not instantiated when the 
            object value of stpxUplinkFastOperEnabled is false(2).
            If the platform does not support the 
            stpxUplinkFastOperEnabled object, then this object is 
            not instantiated when the object value of 
            stpxSpanningTreeType is mst(4)."
    ::= { stpxUplinkFastObjects 2 }

stpxUplinkStationLearningGenRate OBJECT-TYPE
    SYNTAX     Integer32 (0..32000)
    UNITS      "frames"
    MAX-ACCESS read-write
    STATUS     current
    DESCRIPTION
            "The maximum number of station-learning frames that this
            device will generate in each 100 milli-second period after
            a UplinkFast transition.  By configuring this object, the
            network administrator can limit the rate at which
            station-learning frames are generated.  

            If the platform does not support configuration of this
            object when the object value of stpxSpanningTreeType is
            mst(4), then this object is not instantiated."
    ::= { stpxUplinkFastObjects 3 }

stpxUplinkStationLearningFrames OBJECT-TYPE
    SYNTAX     Counter32
    UNITS      "frames"
    MAX-ACCESS read-only
    STATUS     current
    DESCRIPTION
            "The cumulative number of station-learning frames generated
            due to UplinkFast transitions.  All generated
            station-learning frames are included in this counter,
            irrespective of the instance of the Spanning Tree Protocol
            on which the UplinkFast transition occurred.

            If the platform supports the stpxUplinkFastOperEnabled 
            object, then this object is not instantiated when the 
            object value of stpxUplinkFastOperEnabled is false(2).
            If the platform does not support the 
            stpxUplinkFastOperEnabled object, then this object is 
            not instantiated when the object value of 
            stpxSpanningTreeType is mst(4)."
    ::= { stpxUplinkFastObjects 4 }

stpxUplinkFastOperEnabled OBJECT-TYPE
    SYNTAX     TruthValue
    MAX-ACCESS read-only
    STATUS     current
    DESCRIPTION
            "An indication of whether the UplinkFast capability is 
            operationally enabled on the device."
    ::= { stpxUplinkFastObjects 5 }


--
--  Preferred VLANs for Load-Sharing across VLAN Trunk Ports
--

stpxPreferredVlansTable OBJECT-TYPE
    SYNTAX     SEQUENCE OF StpxPreferredVlansEntry
    MAX-ACCESS not-accessible
    STATUS     current
    DESCRIPTION
            "The table containing indications of which VLANs are
            preferred on which VLAN trunk ports.  The preferred
            VLANs on a trunk port have a lower Path Cost value
            compared with the VLANs on the trunk not in the
            preferred list. If the value of stpxSpanningTreeType 
            is neither pvstPlus(1) nor rapidPvstPlus(5), the 
            configuration in this table has no effect. "
    ::= { stpxVlanObjects 1 }

stpxPreferredVlansEntry OBJECT-TYPE
    SYNTAX     StpxPreferredVlansEntry
    MAX-ACCESS not-accessible
    STATUS     current
    DESCRIPTION
            "An entry indicating which VLANs are preferred on a
            specific VLAN trunk port."
    AUGMENTS   { vlanTrunkPortEntry }
    ::= { stpxPreferredVlansTable 1 }

StpxPreferredVlansEntry ::=
    SEQUENCE {
            stpxPreferredVlansMap      OCTET STRING,
            stpxPreferredVlansMap2k    OCTET STRING,
            stpxPreferredVlansMap3k    OCTET STRING,
            stpxPreferredVlansMap4k    OCTET STRING
    }

stpxPreferredVlansMap OBJECT-TYPE
    SYNTAX     OCTET STRING (SIZE (128))
    MAX-ACCESS read-write
    STATUS     current
    DESCRIPTION
            "A string of octets containing one bit per VLAN in the
            management domain on this trunk port.  The first octet
            corresponds to VLANs with VlanIndex values of 0 through 7;
            the second octet to VLANs 8 through 15; etc.  The most
            significant bit of each octet corresponds to the lowest
            value VlanIndex in that octet.

            For each VLAN, if it is preferred on this trunk port, then
            the bit corresponding to that VLAN is set to '1'.
            The default value is 128 bytes of zeros.

            To avoid conflicts between overlapping partial updates by
            multiple managers, i.e., updates which modify only a portion
            of an instance of this object (e.g., enable/disable a single
            VLAN on the trunk port), any SNMP Set operation accessing an
            instance of this object should also write the value of
            vlanTrunkPortSetSerialNo."
    ::= { stpxPreferredVlansEntry 1 }

stpxPreferredVlansMap2k OBJECT-TYPE 
    SYNTAX     OCTET STRING (SIZE (0..128)) 
    MAX-ACCESS read-write 
    STATUS     current 
    DESCRIPTION 
            "A string of octets containing one bit per VLAN for VLANS 
            with VlanIndex values of 1024 through 2047 in the management
            domain on this trunk port.  The first octet corresponds to 
            VLANs with VlanIndex values of 1024 through 1031; 
            the second octet to VLANs 1032 through 1039; etc. 
            The most significant bit of each octet corresponds to the 
            lowest value VlanIndex in that octet. 

            For each VLAN, if it is preferred on this trunk port, then 
            the bit corresponding to that VLAN is set to '1'. 
            The default value is 128 bytes of zeros. 

            To avoid conflicts between overlapping partial updates by 
            multiple managers, i.e., updates which modify only a portion
            of an instance of this object (e.g., enable/disable a single
            VLAN on the trunk port), any SNMP Set operation accessing an
            instance of this object should also write the value of 
            vlanTrunkPortSetSerialNo." 
    ::= { stpxPreferredVlansEntry 2 } 

stpxPreferredVlansMap3k OBJECT-TYPE 
    SYNTAX     OCTET STRING (SIZE (0..128)) 
    MAX-ACCESS read-write 
    STATUS     current 
    DESCRIPTION 
            "A string of octets containing one bit per VLAN for VLANS 
            with VlanIndex values of 2048 through 3071 in the management
            domain on this trunk port.  The first octet corresponds to 
            VLANs with VlanIndex values of 2048 through 2055; 
            the second octet to VLANs 2056 through 2063; etc. 
            The most significant bit of each octet corresponds to the 
            lowest value VlanIndex in that octet. 

            For each VLAN, if it is preferred on this trunk port, then 
            the bit corresponding to that VLAN is set to '1'. 
            The default value is 128 bytes of zeros. 

            To avoid conflicts between overlapping partial updates by 
            multiple managers, i.e., updates which modify only a portion
            of an instance of this object (e.g., enable/disable a single
            VLAN on the trunk port), any SNMP Set operation accessing an
            instance of this object should also write the value of 
            vlanTrunkPortSetSerialNo." 
    ::= { stpxPreferredVlansEntry 3 } 

stpxPreferredVlansMap4k OBJECT-TYPE 
    SYNTAX     OCTET STRING (SIZE (0..128)) 
    MAX-ACCESS read-write 
    STATUS     current 
    DESCRIPTION 
            "A string of octets containing one bit per VLAN for VLANS 
            with VlanIndex values of 3072 through 4095 in the management
            domain on this trunk port.  The first octet corresponds to 
            VLANs with VlanIndex values of 3072 through 3079; 
            the second octet to VLANs 3080 through 3087; etc. 
            The most significant bit of each octet corresponds to the 
            lowest value VlanIndex in that octet. 

            For each VLAN, if it is preferred on this trunk port, then 
            the bit corresponding to that VLAN is set to '1'. 
            The default value is 128 bytes of zeros. 

            To avoid conflicts between overlapping partial updates by 
            multiple managers, i.e., updates which modify only a portion
            of an instance of this object (e.g., enable/disable a single
            VLAN on the trunk port), any SNMP Set operation accessing an
            instance of this object should also write the value of 
            vlanTrunkPortSetSerialNo." 
    ::= { stpxPreferredVlansEntry 4 } 

--
-- Spanning Tree Protocol PVST+ VLAN Configuration 
--

stpxPVSTVlanTable OBJECT-TYPE
        SYNTAX        SEQUENCE OF StpxPVSTVlanEntry
        MAX-ACCESS    not-accessible
        STATUS        current
        DESCRIPTION   "A list of Virtual LAN entries containing
                      information for Spanning Tree PVST+ protocol. 
                      An entry will exist for each VLAN existing on 
                      the device."
        ::= { stpxVlanObjects 2 }

stpxPVSTVlanEntry OBJECT-TYPE
        SYNTAX        StpxPVSTVlanEntry
        MAX-ACCESS    not-accessible
        STATUS        current
        DESCRIPTION   "An entry containing Spanning Tree PVST+ Protocol 
                      information for a particular Virtual LAN."
        INDEX         { stpxPVSTVlanIndex }
        ::= { stpxPVSTVlanTable 1 }

StpxPVSTVlanEntry ::=
        SEQUENCE {
                stpxPVSTVlanIndex
                        VlanIndex,
                stpxPVSTVlanEnable
                        INTEGER
        }

stpxPVSTVlanIndex OBJECT-TYPE
        SYNTAX        VlanIndex
        MAX-ACCESS    not-accessible 
        STATUS        current
        DESCRIPTION   "An index value that uniquely identifies the
                      Virtual LAN associated with this information."
        ::= { stpxPVSTVlanEntry 1 }

stpxPVSTVlanEnable OBJECT-TYPE
        SYNTAX        INTEGER { enabled(1),
                                disabled(2),
                                notApplicable(3) -- read-only
                               }
        MAX-ACCESS    read-write
        STATUS        current
        DESCRIPTION   "Indicates whether Spanning Tree PVST+  
                      Protocol is enabled for this Virtual LAN. If 
                      Spanning Tree PVST+ Protocol is not supported 
                      on this VLAN, then notApplicable(3) will be 
                      returned while retrieving the object value for 
                      this VLAN.

                      If the device only supports a single global
                      Spanning Tree PVST+ Protocol enable/disable 
                      for all the existing VLANs, then the object 
                      value assigned to this VLAN will be applied
                      to the object values of all the instances
                      in this table which do not have the value
                      of notApplicable(3).

                      If the value of stpxSpanningTreeType is neither 
                      pvstPlus(1) nor rapidPvstPlus(5), then the value 
                      of stpxPVSTVlanEnable for this VLAN can not be 
                      changed."
        DEFVAL { enabled }
        ::= { stpxPVSTVlanEntry 2 }
 

--
--  Objects to support Cisco's Shared Spanning Tree Protocol (SSTP).
--
 
stpxInconsistencyTable OBJECT-TYPE
    SYNTAX      SEQUENCE OF StpxInconsistencyEntry
    MAX-ACCESS  not-accessible
    STATUS      current
    DESCRIPTION
                "A table containing a list of the ports for which
                a particular VLAN's Spanning Tree has been found to
                have an inconsistency.  Two types of inconsistency
                are discovered: 1) an inconsistency where two different
                port types have been plugged together; and 2) an
                inconsistency where different switches have different
                PVIDs for the same link."
    ::= { stpxInconsistencyObjects 1 }
 
stpxInconsistencyEntry OBJECT-TYPE
    SYNTAX      StpxInconsistencyEntry
    MAX-ACCESS  not-accessible
    STATUS      current
    DESCRIPTION
                "A VLAN on a particular port for which a Spanning Tree
                inconsistency is currently in effect."
    INDEX { stpxVlanIndex, stpxPortIndex }
    ::= { stpxInconsistencyTable 1 }
 
StpxInconsistencyEntry ::= SEQUENCE {
        stpxVlanIndex          VlanIndex,
        stpxPortIndex          Integer32,
        stpxInconsistentState  BITS
}
 
stpxVlanIndex OBJECT-TYPE
    SYNTAX      VlanIndex
    MAX-ACCESS  not-accessible
    STATUS      current
    DESCRIPTION
             "The VLAN id of the VLAN."
    ::= { stpxInconsistencyEntry 1 }

stpxPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
    ::= { stpxInconsistencyEntry 2 }
 
stpxInconsistentState OBJECT-TYPE
    SYNTAX      BITS {
                     typeInconsistent(0), -- a port-type inconsistency
                     pvidInconsistent(1)  -- a PVID inconsistency
                }
    MAX-ACCESS  read-only
    STATUS      current
    DESCRIPTION
             "The types of inconsistency which have been discovered on
              this port for this VLAN's Spanning Tree.

              When this object exists, the value of the corresponding
              instance of the Bridge MIB's dot1dStpPortState object will
              be 'broken(6)'."
    REFERENCE
             "dot1dStpPortState is defined in RFC-1493."
    ::= { stpxInconsistencyEntry 3 }

--
--  BackboneFast capability
--

stpxBackboneFastEnabled OBJECT-TYPE
    SYNTAX     TruthValue
    MAX-ACCESS read-write
    STATUS     current
    DESCRIPTION
            "An indication of whether the BackboneFast capability is
             administratively enabled on the device."
    ::= { stpxBackboneFastObjects 1 }
 
stpxBackboneFastInInferiorBPDUs OBJECT-TYPE
    SYNTAX     Counter32
    MAX-ACCESS read-only
    STATUS     current
    DESCRIPTION
            "The number of inferior BPDUs received by the switch 
             since the stpxBackboneFastOperEnabled has
             become true(1). If the value of 
             stpxBackboneFastOperEnabled is false(2), then this 
             mib object will have a value of 0."

    ::= { stpxBackboneFastObjects 2 }
 
stpxBackboneFastInRLQRequestPDUs OBJECT-TYPE
    SYNTAX     Counter32
    MAX-ACCESS read-only
    STATUS     current
    DESCRIPTION
            "The number of Root Link Query request PDUs received by the
             switch since the stpxBackboneFastOperEnabled has become
             true(1). If the value of stpxBackboneFastOperEnabled is
             false(2), then this mib object will have a value of 0."

    ::= { stpxBackboneFastObjects 3 }
 
stpxBackboneFastInRLQResponsePDUs OBJECT-TYPE
    SYNTAX     Counter32
    MAX-ACCESS read-only
    STATUS     current
    DESCRIPTION
            "The number of Root Link Query response PDUs received by the
             switch since the stpxBackboneFastOperEnabled has become
             true(1). If the value of stpxBackboneFastOperEnabled is
             false(2), then this mib object will have a value of 0."
    ::= { stpxBackboneFastObjects 4 }
 
stpxBackboneFastOutRLQRequestPDUs OBJECT-TYPE
    SYNTAX     Counter32
    MAX-ACCESS read-only
    STATUS     current
    DESCRIPTION
            "The number of Root Link Query request PDUs transmitted by
             the switch since the stpxBackboneFastOperEnabled has become
             true(1). If the value of stpxBackboneFastOperEnabled is
             false(2), then this mib object will have a value of 0."

    ::= { stpxBackboneFastObjects 5 }
 
stpxBackboneFastOutRLQResponsePDUs OBJECT-TYPE
    SYNTAX     Counter32
    MAX-ACCESS read-only
    STATUS     current
    DESCRIPTION
            "The number of Root Link Query response PDUs transmitted by
             the switch since the stpxBackboneFastOperEnabled has become
             true(1). If the value of stpxBackboneFastOperEnabled is
             false(2), then this mib object will have a value of 0."

    ::= { stpxBackboneFastObjects 6 }

stpxBackboneFastOperEnabled OBJECT-TYPE
    SYNTAX     TruthValue
    MAX-ACCESS read-only
    STATUS     current
    DESCRIPTION
            "An indication of whether the BackboneFast capability is
            operationally enabled on the device."
    ::= { stpxBackboneFastObjects 7 }
 
--
-- STP Root Guard Capability
--

stpxRootGuardConfigTable OBJECT-TYPE
    SYNTAX      SEQUENCE OF StpxRootGuardConfigEntry
    MAX-ACCESS  not-accessible
    STATUS      current
    DESCRIPTION
                "A table containing a list of the bridge ports for which
                Spanning Tree RootGuard capability can be configured."
    ::= { stpxRootGuardObjects 1 }

stpxRootGuardConfigEntry OBJECT-TYPE
    SYNTAX      StpxRootGuardConfigEntry
    MAX-ACCESS  not-accessible
    STATUS      current
    DESCRIPTION
                "A bridge port for which Spanning Tree RootGuard
                capability can be configured."
    INDEX { stpxRootGuardConfigPortIndex }
    ::= { stpxRootGuardConfigTable 1 }

StpxRootGuardConfigEntry ::= SEQUENCE {
    stpxRootGuardConfigPortIndex Integer32,
    stpxRootGuardConfigEnabled   TruthValue
}

stpxRootGuardConfigPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
    ::= { stpxRootGuardConfigEntry 1 }

stpxRootGuardConfigEnabled OBJECT-TYPE
    SYNTAX     TruthValue
    MAX-ACCESS read-write
    STATUS     current
    DESCRIPTION
            "An indication of whether the RootGuard capability is 
            enabled on this port or not. This configuration will be
            applied to all Spanning Tree instances in which this port 
            exists."
    DEFVAL { false }
    ::= { stpxRootGuardConfigEntry 2 }
 
stpxRootInconsistencyTable OBJECT-TYPE
    SYNTAX      SEQUENCE OF StpxRootInconsistencyEntry
    MAX-ACCESS  not-accessible
    STATUS      current
    DESCRIPTION
                "A table containing a list of the bridge ports for which
                a particular Spanning Tree instance has been found 
                to have an root-inconsistency. The agent creates a new 
                entry in this table whenever it detects a new 
                root-inconsistency, and deletes entries 
                when/soon after the inconsistency is no longer present."
    ::= { stpxRootGuardObjects 2 }

stpxRootInconsistencyEntry OBJECT-TYPE
    SYNTAX      StpxRootInconsistencyEntry
    MAX-ACCESS  not-accessible
    STATUS      current
    DESCRIPTION
                "A Spanning Tree instance on a particular port for 
                which a Spanning Tree root-inconsistency is currently 
                in effect."
    INDEX { stpxRootInconsistencyIndex, stpxRootInconsistencyPortIndex }
    ::= { stpxRootInconsistencyTable 1 }

StpxRootInconsistencyEntry ::= SEQUENCE {
        stpxRootInconsistencyIndex Integer32,
        stpxRootInconsistencyPortIndex Integer32,
        stpxRootInconsistencyState     TruthValue
}

stpxRootInconsistencyIndex OBJECT-TYPE
    SYNTAX      Integer32 (0..65535)
    MAX-ACCESS  not-accessible
    STATUS      current
    DESCRIPTION
             "The Spanning Tree instance id, such as the VLAN id
             of the VLAN if the object value of stpxSpanningTreeType
             is pvstPlus(1) or rapidPvstPlus(5)." 
    ::= { stpxRootInconsistencyEntry 1 }

stpxRootInconsistencyPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
     ::= { stpxRootInconsistencyEntry 2 }


stpxRootInconsistencyState OBJECT-TYPE
    SYNTAX      TruthValue
    MAX-ACCESS  read-only
    STATUS      current
    DESCRIPTION
                "Indicates whether the port on a particular Spanning 
                 Tree instance is currently in root-inconsistent 
                 state or not."
    ::= { stpxRootInconsistencyEntry  3 }


--
-- stpxSpanningTreeObjects 
--

stpxSpanningTreeType  OBJECT-TYPE
    SYNTAX      INTEGER  {
                           pvstPlus(1),
                           mistp(2),
                           mistpPvstPlus(3),
                           mst(4),
                           rapidPvstPlus(5)
                }
    MAX-ACCESS  read-write
    STATUS      current
    DESCRIPTION
        "The actual mode of spanning tree protocol runs
        on the  device. It can be one of the following:

        pvstPlus -- PVST+ (Per VLAN Spanning Tree+ Protocol).

        mistp -- MISTP (Multi Instance Spanning Tree Protocol).

        mistpPvstPlus --  MISTP with the tunneling scheme
                             enabled for PVST+.

        mst -- IEEE 802.1s Multiple Spanning Tree (MST)
               with IEEE 802.1w Rapid Spanning Tree Protocol
               (RSTP).

        rapidPvstPlus -- IEEE 802.1w Rapid Spanning Tree 
                Protocol (RSTP) for all vlans in PVST+.

        When the value of this MIB object gets changed, the 
        network connectivity would be affected and the 
        connectivity to this device would also be lost 
        temporarily."
    DEFVAL  { pvstPlus }
     ::= { stpxSpanningTreeObjects 1}

stpxSpanningTreePathCostMode    OBJECT-TYPE
    SYNTAX     INTEGER {
                        short(1), -- 16 bits spanning tree path
                                  -- cost mode
                        long(2)   -- 32 bits spanning tree path
                                  -- cost mode
                       }
    MAX-ACCESS read-write
    STATUS     current
    DESCRIPTION
        "Indicate the type of spanning tree path cost mode configured
        on device. This mode applies to all instances of the Spanning
        Tree protocol running on the device.

        When the value of this MIB object gets changed, the path cost
        of all ports will be reassigned to the default path cost
        values based on the new spanning tree path cost mode and the
        ports' speed.

        When the value of this MIB object is set to long(2),
        the stpxLongStpPortPathCost MIB object must be used in order
        to retrieve/configure the spanning tree port path cost as a
        32 bits value. The set operation on dot1dStpPortPathCost in
        BRIDGE-MIB will be rejected. While retrieving the value of
        dot1dStpPortPathCost, the maximum value of 65535 will be
        returned if the value of stpxLongStpPortPathCost for the same
        instance exceeds 65535.

        When the value of this MIB object is set to short(1),
        the dot1dStpPortPathCost in BRIDGE-MIB must be used."
   DEFVAL  { short }
   ::= { stpxSpanningTreeObjects 2 }


stpxLongStpPortPathCostTable OBJECT-TYPE
      SYNTAX      SEQUENCE OF StpxLongStpPortPathCostEntry
      MAX-ACCESS  not-accessible
      STATUS      current
      DESCRIPTION
        "A table containing the spanning tree port path cost
        configuration when stpxSpanningTreePathCostMode is
        long(2),

        If the value of stpxSpanningTreePathCostMode is short(1),
        this table is not instantiated."
    ::= { stpxSpanningTreeObjects 3 }

stpxLongStpPortPathCostEntry OBJECT-TYPE
    SYNTAX      StpxLongStpPortPathCostEntry
    MAX-ACCESS  not-accessible
    STATUS      current
    DESCRIPTION
        "A conceptual row containing the spanning tree port path cost
         configuration."
     AUGMENTS   { dot1dStpPortEntry }
    ::= { stpxLongStpPortPathCostTable 1 }

StpxLongStpPortPathCostEntry ::= SEQUENCE {
        stpxLongStpPortPathCost Unsigned32
}

stpxLongStpPortPathCost OBJECT-TYPE
    SYNTAX      Unsigned32
    MAX-ACCESS  read-write
    STATUS      current
    DESCRIPTION
         "The contribution of this port to the path cost (in 32
          bits value) of paths towards the spanning tree root which
          include this port.

          This object is used to configure the spanning tree port
          path cost in 32 bits value range when the
          stpxSpanningTreePathCostMode is long(2).

          If the stpxSpanningTreePathCostMode is short(1), this mib
          object is not instantiated."
    ::= { stpxLongStpPortPathCostEntry 1}

stpxExtendedSysIDAdminEnabled OBJECT-TYPE
    SYNTAX     TruthValue
    MAX-ACCESS read-write
    STATUS     current
    DESCRIPTION
          "Indicates whether Extended System ID feature 
           is administratively enabled on the device or not."
    REFERENCE
               "IEEE 802.1t."
    ::= { stpxSpanningTreeObjects 4 }

stpxExtendedSysIDOperEnabled OBJECT-TYPE
    SYNTAX     TruthValue
    MAX-ACCESS read-only
    STATUS     current
    DESCRIPTION
          "Indicates whether Extended System ID feature 
           is operationaly enabled on the device or not.

           If the value of this object is true(1), then
           the accepted values for dot1dStpPriority
           in BRIDGE-MIB should be multiples of 4096 plus
           bridge instance ID, such as VlanIndex. Changing
           this object value might cause the values of
           dot1dBaseBridgeAddress and dot1dStpPriority
           in BRIDGE-MIB to be changed also."
    REFERENCE
               "IEEE 802.1t."
    ::= { stpxSpanningTreeObjects 5 }

stpxNotificationEnable OBJECT-TYPE
    SYNTAX      BITS {
                      newRoot(0),
                      topologyChange(1),
                      inconsistency(2),
                      rootInconsistency(3),
                      loopInconsistency(4)
                }
    MAX-ACCESS  read-write
    STATUS      current
    DESCRIPTION
         "Indicates whether a specified notification is enabled or not.
         If a bit corresponding to a notification is set to 1, then 
         the specified notification can be generated.

         newRoot -- the newRoot notification as defined in BRIDGE-MIB.

         topologyChange -- the topologyChange notification as
                           defined in BRIDGE-MIB.

         inconsistency -- the stpxInconsistencyUpdate notification.

         rootInconsistency -- the stpxRootInconsistencyUpdate 
                              notification.

         loopInconsistency -- the stpxLoopInconsistencyUpdate 
                              notification."
    ::= { stpxSpanningTreeObjects 6 }


-- MISTP Objects


stpxMISTPInstanceNumber  OBJECT-TYPE
    SYNTAX      Integer32 (1..256)
    MAX-ACCESS  read-only
    STATUS      current
    DESCRIPTION
       "The number of MISTP instances, that are supported by the device 
       when the value of stpxSpanningTreeType is either mistp(2)
       or mistpPvstPlus(3)."
     ::= { stpxMISTPObjects 1}


-- When stpxSpanningTreeType is modified from a value of 'pvstPlus' to 
-- either 'mistp' or 'mistpPvstPlus', the agent will create a fixed  
-- number (specified in stpxMISTPInstanceNumber) of MISTP instances in
-- this table. When stpxSpanningTreeType is changed to 'pvstPlus', the 
-- agent will delete all the MISTP instances from this table and also 
-- all the MIB objects associated with them.

stpxMISTPInstanceTable OBJECT-TYPE
    SYNTAX      SEQUENCE OF StpxMISTPInstanceEntry
    MAX-ACCESS  not-accessible
    STATUS      current
    DESCRIPTION
          "This table contains one entry for each instance of MISTP and 
          it contains stpxMISTPInstanceNumber entries, numbered from 1
          to stpxMISTPInstanceNumber.

          This table is only instantiated when the value of 
          stpxSpanningTreeType is mistp(2) or mistpPvstPlus(3)."
     ::= {stpxMISTPObjects 2 }

stpxMISTPInstanceEntry OBJECT-TYPE
      SYNTAX      StpxMISTPInstanceEntry
      MAX-ACCESS  not-accessible
      STATUS      current
      DESCRIPTION
          "A conceptual row containing the status of the MISTP 
          instance."
      INDEX  { stpxMISTPInstanceIndex }
      ::= { stpxMISTPInstanceTable 1 }

StpxMISTPInstanceEntry ::= SEQUENCE {
       stpxMISTPInstanceIndex  Integer32,
       stpxMISTPInstanceEnable TruthValue,
       stpxMISTPInstanceVlansMapped OCTET STRING,
       stpxMISTPInstanceVlansMapped2k OCTET STRING,
       stpxMISTPInstanceVlansMapped3k OCTET STRING,
       stpxMISTPInstanceVlansMapped4k OCTET STRING
}

stpxMISTPInstanceIndex OBJECT-TYPE
      SYNTAX      Integer32 (1..256)
      MAX-ACCESS  not-accessible
      STATUS      current
      DESCRIPTION
          "An arbitrary integer within the range from 1 to the value of
          stpxMISTPInstanceNumber that uniquely identifies an instance."
      ::= {stpxMISTPInstanceEntry 1 }

stpxMISTPInstanceEnable  OBJECT-TYPE
      SYNTAX        TruthValue
      MAX-ACCESS    read-write
      STATUS        current
      DESCRIPTION 
          "This object indicates whether the MISTP protocol is currently
          enabled on the MISTP instance.
      
          If this object is set to
             'true'    - the MISTP protocol will run on this instance.
                        
             'false'   - the MISTP protocol will stop running on this 
                         instance.
          "
      DEFVAL { true }     
      ::= {stpxMISTPInstanceEntry 2 }     

stpxMISTPInstanceVlansMapped OBJECT-TYPE
    SYNTAX     OCTET STRING (SIZE (0..128))
    MAX-ACCESS read-only
    STATUS     current
    DESCRIPTION
            "A string of octets containing one bit per VLAN. The
            first octet corresponds to VLANs with VlanIndex values
            of 0 through 7; the second octet to VLANs 8 through
            15; etc.  The most significant bit of each octet
            corresponds to the lowest value VlanIndex in that octet.

            For each VLAN, if it is mapped to this MISTP instance,
            then the bit corresponding to that VLAN is set to '1'."
    ::= {stpxMISTPInstanceEntry 3 }

stpxMISTPInstanceVlansMapped2k OBJECT-TYPE
    SYNTAX     OCTET STRING (SIZE (0..128))
    MAX-ACCESS read-only
    STATUS     current
    DESCRIPTION
            "A string of octets containing one bit per VLAN for
            VLANS with VlanIndex values of 1024 through 2047. The
            first octet corresponds to VLANs with VlanIndex values
            of 1024 through 1031; the second octet to VLANs 1032
            through 1039; etc.  The most significant bit of each
            octet corresponds to the lowest value VlanIndex in that
            octet.

            For each VLAN, if it is mapped to this MISTP instance,
            then the bit corresponding to that VLAN is set to '1'.
            
            This object is only instantiated on devices with 
            support for VlanIndex up to 4095."
    ::= {stpxMISTPInstanceEntry 4 }

stpxMISTPInstanceVlansMapped3k OBJECT-TYPE
    SYNTAX     OCTET STRING (SIZE (0..128))
    MAX-ACCESS read-only
    STATUS     current
    DESCRIPTION
            "A string of octets containing one bit per VLAN for
            VLANS with VlanIndex values of 2048 through 3071. The
            first octet corresponds to VLANs with VlanIndex values
            of 2048 through 2055; the second octet to VLANs 2056
            through 2063; etc.  The most significant bit of each
            octet corresponds to the lowest value VlanIndex in that
            octet.

            For each VLAN, if it is mapped to this MISTP instance,
            then the bit corresponding to that VLAN is set to '1'.

            This object is only instantiated on devices with 
            support for VlanIndex up to 4095."
    ::= {stpxMISTPInstanceEntry 5 }

stpxMISTPInstanceVlansMapped4k OBJECT-TYPE
    SYNTAX     OCTET STRING (SIZE (0..128))
    MAX-ACCESS read-only
    STATUS     current
    DESCRIPTION
            "A string of octets containing one bit per VLAN for
            VLANS with VlanIndex values of 3072 through 4095. The
            first octet corresponds to VLANs with VlanIndex values
            of 3072 through 3079; the second octet to VLANs 3080
            through 3087; etc.  The most significant bit of each
            octet corresponds to the lowest value VlanIndex in that
            octet.

            For each VLAN, if it is mapped to this MISTP instance,
            then the bit corresponding to that VLAN is set to '1'.

            This object is only instantiated on devices with 
            support for VlanIndex up to 4095."
    ::= {stpxMISTPInstanceEntry 6 }


stpxVlanMISTPInstMapTable OBJECT-TYPE
      SYNTAX      SEQUENCE OF StpxVlanMISTPInstMapEntry
      MAX-ACCESS  not-accessible
      STATUS      current
      DESCRIPTION
        "A table containing the MISTP Instance Index of the VLANs for a
        particular management domain. 

        This table is only instantiated when the value of  
        stpxSpanningTreeType is mistp(2) or mistpPvstPlus(3)."
    ::= { stpxMISTPObjects 3 }

stpxVlanMISTPInstMapEntry OBJECT-TYPE
    SYNTAX      StpxVlanMISTPInstMapEntry
    MAX-ACCESS  not-accessible
    STATUS      current
    DESCRIPTION
        "A conceptual row containing the MISTP Instance Index of the 
        VLAN for a particular management domain."
     AUGMENTS   { vtpVlanEntry  }
    ::= { stpxVlanMISTPInstMapTable 1 }

StpxVlanMISTPInstMapEntry ::= SEQUENCE {
        stpxVlanMISTPInstMapInstIndex Integer32
}

stpxVlanMISTPInstMapInstIndex OBJECT-TYPE
    SYNTAX      Integer32 (0..256)
    MAX-ACCESS  read-only
    STATUS      current
    DESCRIPTION
         "The MISTP instance, to which the corresponding vlan is mapped.
         If this value of this mib object is 0,  the corresponding vlan 
         is not configured to be mapped to any MISTP instance and all
         the ports under this VLAN remain in blocking state." 
    ::= { stpxVlanMISTPInstMapEntry 1}

stpxVlanMISTPInstMapEditTable OBJECT-TYPE
    SYNTAX      SEQUENCE OF StpxVlanMISTPInstMapEditEntry
    MAX-ACCESS  not-accessible
    STATUS      current
    DESCRIPTION
        "A table containing the MISTP related information for the VLANs 
        in the Edit Buffers for a particular management domain.
        
        This table is only instantiated when when the value of
        stpxSpanningTreeType is mistp(2) or mistpPvstPlus(3)." 
    ::= { stpxMISTPObjects 4 }

stpxVlanMISTPInstMapEditEntry OBJECT-TYPE
    SYNTAX      StpxVlanMISTPInstMapEditEntry
    MAX-ACCESS  not-accessible
    STATUS      current
    DESCRIPTION
        "Information about one VLAN mapping to one instance 
        in the Edit Buffer for a particular management domain."
     AUGMENTS   { vtpVlanEditEntry  }
    ::= { stpxVlanMISTPInstMapEditTable 1 }

StpxVlanMISTPInstMapEditEntry ::= SEQUENCE {
        stpxVlanMISTPInstMapEditInstIndex Integer32
}

stpxVlanMISTPInstMapEditInstIndex OBJECT-TYPE
    SYNTAX      Integer32 (0..256)
    MAX-ACCESS  read-create
    STATUS      current
    DESCRIPTION
         "The MISTP instance, to which the corresponding vlan would be 
          mapped. The value of this mib object is from 0 to the value of
          stpxMISTPInstanceNumber. If setting the value of this object
          to 0, the corresponding vlan will not be mapped to a MISTP 
          instance and all the ports under this VLAN will be moved into
          the blocking state."
    ::= { stpxVlanMISTPInstMapEditEntry 1 }

stpxPreferredMISTPInstancesTable OBJECT-TYPE
    SYNTAX     SEQUENCE OF StpxPreferredMISTPInstancesEntry
    MAX-ACCESS not-accessible
    STATUS     current
    DESCRIPTION
            "The table containing indications of which MISTP instances
            are preferred on which  trunk ports.  The preferred
            MISTP instances on a trunk port have a lower Path Cost value
            compared with the MISTP instances on the trunk not in the
            preferred list. 

            This table is only instantiated when the value of
            stpxSpanningTreeType is mistp(2) or mistpPvstPlus(3)." 
    ::= { stpxMISTPObjects 5 }

stpxPreferredMISTPInstancesEntry OBJECT-TYPE
    SYNTAX     StpxPreferredMISTPInstancesEntry
    MAX-ACCESS not-accessible
    STATUS     current
    DESCRIPTION
            "An entry indicating which MISTP instances are preferred on
            a specific trunk port."
    AUGMENTS   { vlanTrunkPortEntry }
    ::= { stpxPreferredMISTPInstancesTable 1 }

StpxPreferredMISTPInstancesEntry ::=
    SEQUENCE {
            stpxPreferredMISTPInstancesMap      OCTET STRING
    }

stpxPreferredMISTPInstancesMap OBJECT-TYPE
    SYNTAX     OCTET STRING(SIZE(1..32))
    MAX-ACCESS read-write
    STATUS     current
    DESCRIPTION
            "A string of octets containing one bit per MISTP instances 
            in the management domain on this trunk port. The first octet
            corresponds to MISTP instances with InstIndex values of 1 
            through 8; the second octet to MISTP instances 9 through 16;
            etc. The most significant bit of each octet corresponds to 
            the lowest value instanceIndex in that octet. The number of 
            bits for this mib object will be determined by the value of 
            stpxMISTPInstanceNumber.

            For each instance, if it is preferred on this trunk port,
            then the bit corresponding to that instance is set to '1'.


            To avoid conflicts between overlapping partial updates by
            multiple managers, i.e., updates which modify only a portion
            of an instance of this object (e.g., enable/disable a single
            instance on the trunk port), any SNMP Set operation 
            accessing an instance of this object should also write the 
            value of vlanTrunkPortSetSerialNo."

    ::= { stpxPreferredMISTPInstancesEntry 1 }

--
-- STP Loop Guard Capability
--

stpxLoopGuardConfigTable OBJECT-TYPE
    SYNTAX      SEQUENCE OF StpxLoopGuardConfigEntry
    MAX-ACCESS  not-accessible
    STATUS      current
    DESCRIPTION
                "A table containing a list of the bridge ports for which
                Spanning Tree LoopGuard capability can be configured."
    ::= { stpxLoopGuardObjects 1 }

stpxLoopGuardConfigEntry OBJECT-TYPE
    SYNTAX      StpxLoopGuardConfigEntry
    MAX-ACCESS  not-accessible
    STATUS      current
    DESCRIPTION
                "A bridge port for which Spanning Tree LoopGuard 
                capability can be configured."
    INDEX { stpxLoopGuardConfigPortIndex }
    ::= { stpxLoopGuardConfigTable 1 }

StpxLoopGuardConfigEntry ::= SEQUENCE {
    stpxLoopGuardConfigPortIndex Integer32,
    stpxLoopGuardConfigEnabled   TruthValue,
    stpxLoopGuardConfigMode INTEGER
}

stpxLoopGuardConfigPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
    ::= { stpxLoopGuardConfigEntry 1 }

stpxLoopGuardConfigEnabled OBJECT-TYPE
    SYNTAX     TruthValue
    MAX-ACCESS read-write
    STATUS     deprecated 
    DESCRIPTION
            "An indication of whether the LoopGuard capability is 
            enabled on this port or not. This configuration will be
            applied to all the Spanning Tree instances in which this 
            port exists.

            In order to support additional Loop Guard config mode
            (default) as defined in stpxLoopGuardConfigMode other 
            than enable (true(1)) or disable (false(2)) as defined 
            in this object, stpxLoopGuardConfigMode object needs to 
            be used.

            When the stpxLoopGuardConfigMode object has the value of
            enable(1), the value of stpxLoopGuardConfigEnabled for 
            the same instance will be true(1). When the 
            stpxLoopGuardConfigMode object has the value of disable(2), 
            the value of stpxLoopGuardConfigEnabled for the same 
            instance will be false(2). When the stpxLoopGuardConfigMode 
            object has the value of default(3), the value of 
            stpxLoopGuardConfigEnabled for the same instance will 
            depend on the object value of 
            stpxLoopGuardGlobalDefaultMode."
    DEFVAL { false }
    ::= { stpxLoopGuardConfigEntry 2 }


stpxLoopGuardConfigMode OBJECT-TYPE
    SYNTAX     INTEGER {
                        enable(1),
                        disable(2), 
                        default(3)  
               }
    MAX-ACCESS read-write
    STATUS     current 
    DESCRIPTION
               "Indicates the mode of Loop Guard Feature on this 
               port. This configuration will be applied to all 
               the Spanning Tree instances in which this port 
               exists.

               enable -- the Loop Guard feature is enabled on this 
                         port. 

               disable -- the Loop Guard feature is disabled on this 
                         port.  

               default -- whether the Loop Guard feature is enabled
                          or not on this port depends on the object 
                          value of stpxLoopGuardGlobalDefaultMode." 
    ::= { stpxLoopGuardConfigEntry 3 }

stpxLoopInconsistencyTable OBJECT-TYPE
    SYNTAX      SEQUENCE OF StpxLoopInconsistencyEntry
    MAX-ACCESS  not-accessible
    STATUS      current
    DESCRIPTION
                "A table containing a list of the bridge ports for which
                a particular Spanning Tree instance has been found
                to have a loop-inconsistency. The agent creates a new
                entry in this table whenever it detects a new
                loop-inconsistency, and deletes entries
                when/soon after the inconsistency is no longer present."
    ::= { stpxLoopGuardObjects 2 }

stpxLoopInconsistencyEntry OBJECT-TYPE
    SYNTAX      StpxLoopInconsistencyEntry
    MAX-ACCESS  not-accessible
    STATUS      current
    DESCRIPTION
                "A Spanning Tree instance on a particular port for
                which a Spanning Tree loop-inconsistency is currently
                in effect."
    INDEX { stpxLoopInconsistencyIndex, 
            stpxLoopInconsistencyPortIndex }
    ::= { stpxLoopInconsistencyTable 1 }

StpxLoopInconsistencyEntry ::= SEQUENCE {
        stpxLoopInconsistencyIndex Integer32,
        stpxLoopInconsistencyPortIndex Integer32,
        stpxLoopInconsistencyState     TruthValue
}

stpxLoopInconsistencyIndex OBJECT-TYPE
    SYNTAX      Integer32 (0..65535)
    MAX-ACCESS  not-accessible
    STATUS      current
    DESCRIPTION
            "The Spanning Tree instance id, such as the VLAN id
             of the VLAN if the object value of stpxSpanningTreeType
             is pvstPlus(1) or rapidPvstPlus(5)." 
    ::= { stpxLoopInconsistencyEntry 1 }

stpxLoopInconsistencyPortIndex OBJECT-TYPE
    SYNTAX      Integer32 (1..65535)
    MAX-ACCESS  not-accessible
    STATUS      current
    DESCRIPTION
                "The value of dot1dBasePort (i.e. dot1dBridge.1.4)
                 for the bridge port."
    REFERENCE
                "dot1dBasePort is defined in RFC1493."
    ::= { stpxLoopInconsistencyEntry 2 }

stpxLoopInconsistencyState OBJECT-TYPE
    SYNTAX      TruthValue
    MAX-ACCESS  read-only
    STATUS      current
    DESCRIPTION
                "Indicates whether the port on a particular Spanning 
                 Tree instance is currently in loop-inconsistent 
                 state or not."
    ::= { stpxLoopInconsistencyEntry  3 }

stpxLoopGuardGlobalDefaultMode OBJECT-TYPE
    SYNTAX      INTEGER {
                         enable(1),
                         disable(2)
                } 
    MAX-ACCESS  read-write
    STATUS      current
    DESCRIPTION
                "Indicates the global default config mode of LoopGuard 
                feature on the device."  
    ::= { stpxLoopGuardObjects 3 }


--
-- Spanning Tree Port Fast Start Objects
--

stpxFastStartBpduGuardEnable OBJECT-TYPE
        SYNTAX        TruthValue
        MAX-ACCESS    read-write
        STATUS        current
        DESCRIPTION   "Indicates the global default mode of the Bpdu
                      Guard feature on the device.

                      On platforms that does not support per port 
                      Bpdu Guard configuration as indicated by
                      the object stpxFastStartPortBpduGuardMode,
                      if  the value of this object is set to true(1), 
                      and the Fast Start Feature is operationally 
                      enabled on a port, then that port will be 
                      immediately disabled when the system receives
                      a BPDU from that port." 
        DEFVAL { false }
     ::= { stpxFastStartObjects 1 }

stpxFastStartBpduFilterEnable OBJECT-TYPE
        SYNTAX        TruthValue
        MAX-ACCESS    read-write
        STATUS        current
        DESCRIPTION   "Indicates the global default mode of the Bpdu 
                      Filter feature on the device.

                      On platforms that does not support per port 
                      Bpdu Filter configuration as indicated by
                      the object stpxFastStartPortBpduFilterMode,
                      if  the value of this object is set to true(1), 
                      and the Fast Start Feature is operationally 
                      enabled on a port, then no BPDUs will be 
                      transmitted on this port."   
        DEFVAL { false }
        ::= { stpxFastStartObjects 2 }

stpxFastStartPortTable OBJECT-TYPE
    SYNTAX      SEQUENCE OF StpxFastStartPortEntry
    MAX-ACCESS  not-accessible
    STATUS      current
    DESCRIPTION
                "A table containing a list of the bridge ports for
                which Spanning Tree Port Fast Start can be
                configured."
    ::= { stpxFastStartObjects 3 }

stpxFastStartPortEntry OBJECT-TYPE
    SYNTAX      StpxFastStartPortEntry
    MAX-ACCESS  not-accessible
    STATUS      current
    DESCRIPTION
                "A bridge port for which Spanning Tree Port Fast
                Start can be configured."
    INDEX { stpxFastStartPortIndex }
    ::= { stpxFastStartPortTable 1 }

StpxFastStartPortEntry ::= SEQUENCE {
    stpxFastStartPortIndex Integer32,
    stpxFastStartPortEnable   TruthValue,
    stpxFastStartPortMode  INTEGER,
    stpxFastStartPortBpduGuardMode INTEGER, 
    stpxFastStartPortBpduFilterMode INTEGER
}

stpxFastStartPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
    ::= { stpxFastStartPortEntry 1 }

stpxFastStartPortEnable OBJECT-TYPE
    SYNTAX     TruthValue
    MAX-ACCESS read-write
    STATUS     deprecated 
    DESCRIPTION
               "Indicates whether the port is operating in spantree
               fast start mode.  A port with fast start enabled is
               immediately put in spanning tree forwarding state when
               that port is detected by the Spanning Tree, rather 
               than starting in blocking state which is the normal 
               operation.

               In order to support additional Fast Start enable mode
               (enableForTrunk and default) as defined in
               stpxFastStartPortMode other than enable (true(1))
               or disable (false(2)) as defined in this object,
               stpxFastStartPortMode object needs to be used.

               When the stpxFastStartPortMode has the value of
               enable(1) or enableForTrunk(3), the value of
               stpxFastStartPortEnable for the same instance
               will be true(1). When the stpxFastStartPortMode
               has the value of disable(2), the value of 
               stpxFastStartPortEnable for the same instance will be 
               false(2). When the stpxFastStartPortMode has the value 
               of default(4), the value of stpxFastStartPortEnable for 
               the same instance depends on the object value of 
               stpxFastStartGlobalDefaultMode."
    DEFVAL { false }
    ::= { stpxFastStartPortEntry 2 }

stpxFastStartPortMode OBJECT-TYPE
    SYNTAX     INTEGER {
                        enable(1),
                        disable(2), 
                        enableForTrunk(3),
                        default(4)  
               }
    MAX-ACCESS read-write
    STATUS     current 
    DESCRIPTION
               "Indicates the mode of Fast Start Feature on the 
               port. A port with fast start enabled is immediately 
               put in spanning tree forwarding state when the port
               is detected by the Spanning Tree, rather than 
               starting in blocking state which is the normal 
               operation.

               enable -- the fast start feature is enabled on this 
                         port but will only take effect when the 
                         object value of its 
                         vlanTrunkPortDynamicStatus as specified 
                         in CISCO-VTP-MIB is notTrunking(2).

               disable -- the fast start feature is disabled on this 
                         port.  
  
               enableForTrunk -- the fast start feature is enabled 
                         on this port and will take effect 
                         regardless of the object value of 
                         its vlanTrunkPortDynamicStatus.

               default -- whether the fast start feature is enabled
                          or not on this port depends on the object 
                          value of stpxFastStartGlobalDefaultMode."
    ::= { stpxFastStartPortEntry 3 }

stpxFastStartPortBpduGuardMode OBJECT-TYPE
    SYNTAX     INTEGER {
                        enable(1),
                        disable(2),
                        default(3)
               }
    MAX-ACCESS read-write
    STATUS     current
    DESCRIPTION
               "Indicates the mode of Bpdu Guard Feature on the
               port. A port with Bpdu Guard enabled is 
               immediately disabled when the system 
               receives a BPDU from that port. 

               enable -- the Bpdu Guard feature is enabled on this
                         port. 

               disable -- the Bpdu Guard feature is disabled on this
                         port.
 
               default -- whether the Bpdu Guard feature is enabled
                          or not on this port depends on the object
                          value of stpxFastStartBpduGuardEnable. If 
                          the value of stpxFastStartBpduGuardEnable
                          is true(1) and Fast Start feature is also 
                          enabled operationally on this port, then
                          this port is immediately disabled when 
                          the system receives a BPDU from this port."
    DEFVAL { default }
    ::= { stpxFastStartPortEntry 4 }

stpxFastStartPortBpduFilterMode OBJECT-TYPE
    SYNTAX     INTEGER {
                        enable(1),
                        disable(2),
                        default(3)
               }
    MAX-ACCESS read-write
    STATUS     current
    DESCRIPTION
               "Indicates the mode of Bpdu Filter Feature on the
               port. The system will not transmit BPDUs on a port 
               with Bpdu Filter feature enabled.

               enable -- the Bpdu Filter feature is enabled on this 
                         port. 

               disable -- the Bpdu Filter feature is disabled on this
                          port.
  
               default -- whether the Bpdu Filter feature is enabled
                          or not on this port depends on the object
                          value of stpxFastStartBpduFilterEnable. If
                          the value of stpxFastStartBpduFilterEnable
                          is true(1) and Fast Start feature is also
                          enabled operationally on this port, then
                          no BPDUs will be transmitted on this port." 
    DEFVAL { default }
    ::= { stpxFastStartPortEntry 5 }


stpxFastStartGlobalDefaultMode OBJECT-TYPE
    SYNTAX     INTEGER {
                        enable(1),
                        disable(2)
               }
    MAX-ACCESS    read-write
    STATUS        current
    DESCRIPTION   
               "Indicates the global default mode of the Fast 
               Start feature on the device."  
    DEFVAL { disable }
    ::= { stpxFastStartObjects 4 }

stpxFastStartOperModeTable OBJECT-TYPE
    SYNTAX      SEQUENCE OF StpxFastStartOperModeEntry
    MAX-ACCESS  not-accessible
    STATUS      current
    DESCRIPTION 
         "A table containing a list of the bridge ports 
         for a particular Spanning Tree Instance."
    ::= { stpxFastStartObjects 5 }
    
stpxFastStartOperModeEntry OBJECT-TYPE
    SYNTAX      StpxFastStartOperModeEntry
    MAX-ACCESS  not-accessible
    STATUS      current
    DESCRIPTION
         "An entry with port fast start oper mode 
         information on a bridge port for a particular 
         Spanning Tree Instance."
    INDEX { stpxFastStartOperModeInstIndex,
            stpxFastStartOperModePortIndex }
    ::= { stpxFastStartOperModeTable 1 }

StpxFastStartOperModeEntry ::= SEQUENCE {
    stpxFastStartOperModeInstIndex  Integer32,
    stpxFastStartOperModePortIndex  Integer32,
    stpxFastStartOperMode  INTEGER 
}

stpxFastStartOperModeInstIndex OBJECT-TYPE
    SYNTAX      Integer32 (0..65535)
    MAX-ACCESS  not-accessible
    STATUS      current
    DESCRIPTION
        "The Spanning Tree instance id, such as the VLAN id 
        of the VLAN if the object value of stpxSpanningTreeType
        is pvstPlus(1)."
    ::= { stpxFastStartOperModeEntry 1 }

stpxFastStartOperModePortIndex OBJECT-TYPE
    SYNTAX      Integer32 (1..65535)
    MAX-ACCESS  not-accessible
    STATUS      current
    DESCRIPTION
        "The value of dot1dBasePort (i.e. dot1dBridge.1.4)
        for the bridge port."
    REFERENCE
        "dot1dBasePort is defined in RFC1493."
    ::= { stpxFastStartOperModeEntry 2 }

stpxFastStartOperMode OBJECT-TYPE
    SYNTAX      INTEGER {
                     enabled(1),
                     disabled(2)
                }
    MAX-ACCESS read-only
    STATUS     current
    DESCRIPTION
        "Indicates the fast start operational status of the 
        port on a particular Spanning Tree Instance."
   ::= { stpxFastStartOperModeEntry 3 }

--
-- BPDU Skewing Feature
--
stpxBpduSkewingDetectionEnable OBJECT-TYPE
    SYNTAX     TruthValue
    MAX-ACCESS read-write
    STATUS     current
    DESCRIPTION
               "Indicates whether BPDU skewing detection feature
               is enabled or not on the system. If this object has
               the value of true(1), then the system will detect
               whether BPDUs received by any port on any Spanning 
               Tree instance are processed at an interval longer
               than the object value of dot1dStpHelloTime in the
               BIRDGE-MIB of the Spanning Tree instance."
    DEFVAL { false }
    ::= { stpxBpduSkewingObjects 1 }

stpxBpduSkewingTable OBJECT-TYPE
    SYNTAX      SEQUENCE OF StpxBpduSkewingEntry
    MAX-ACCESS  not-accessible
    STATUS      current
    DESCRIPTION
                "A table containing a list of the bridge ports for 
                which a particular Spanning Tree instance has been 
                detected to have BPDU skewing occurred since the 
                object value of stpxBpduSkewingDetectionEnable was
                last changed to true(1).

                The agent creates a new entry in this table whenever
                a port in a particular Spanning Tree instance is 
                detected to be BPDU skewed since the object value of 
                stpxBpduSkewingDetectionEnable object is changed to 
                true(1). The agent deletes all the entries in this 
                table when the object value of 
                stpxBpduSkewingDetectionEnable is changed to false(2)
                or the object value of stpxSpanningTreeType is 
                changed."
    ::= { stpxBpduSkewingObjects 2 }

stpxBpduSkewingEntry OBJECT-TYPE
    SYNTAX      StpxBpduSkewingEntry
    MAX-ACCESS  not-accessible
    STATUS      current
    DESCRIPTION
                "A Spanning Tree instance on a particular port for
                which BPDU skewing has been detected."
    INDEX { stpxBpduSkewingInstanceIndex,
            stpxBpduSkewingPortIndex }
    ::= { stpxBpduSkewingTable 1 }

StpxBpduSkewingEntry ::= SEQUENCE {
        stpxBpduSkewingInstanceIndex Integer32,
        stpxBpduSkewingPortIndex Integer32,
        stpxBpduSkewingLastSkewDuration Unsigned32,
        stpxBpduSkewingWorstSkewDuration Unsigned32,
        stpxBpduSkewingWorstSkewTime TimeStamp
}

stpxBpduSkewingInstanceIndex OBJECT-TYPE
    SYNTAX      Integer32 (0..65535) 
    MAX-ACCESS  not-accessible
    STATUS      current
    DESCRIPTION
             "The Spanning Tree instance id, such as the VLAN id 
             of the VLAN if the object value of stpxSpanningTreeType 
             is pvstPlus(1)." 
    ::= { stpxBpduSkewingEntry 1 }

stpxBpduSkewingPortIndex OBJECT-TYPE
    SYNTAX      Integer32 (1..65535)
    MAX-ACCESS  not-accessible
    STATUS      current
    DESCRIPTION
                "The value of dot1dBasePort (i.e. dot1dBridge.1.4)
                 for the bridge port."
    REFERENCE
               "dot1dBasePort is defined in RFC1493."
     ::= { stpxBpduSkewingEntry 2 }

stpxBpduSkewingLastSkewDuration OBJECT-TYPE
    SYNTAX      Unsigned32
    UNITS       "milliseconds"
    MAX-ACCESS  read-only
    STATUS      current
    DESCRIPTION
                "Indicates the skew duration in milliseconds of the
                last BPDU skewing detected."
    ::= { stpxBpduSkewingEntry  3 }

stpxBpduSkewingWorstSkewDuration OBJECT-TYPE
    SYNTAX      Unsigned32
    UNITS       "milliseconds"
    MAX-ACCESS  read-only
    STATUS      current
    DESCRIPTION
                "Indicates the skew duration in milliseconds of the
                worst BPDU skewing detected."
    ::= { stpxBpduSkewingEntry  4 }

stpxBpduSkewingWorstSkewTime OBJECT-TYPE
    SYNTAX      TimeStamp
    MAX-ACCESS  read-only
    STATUS      current
    DESCRIPTION
                "Indicates the value of sysUpTime when the worst
                BPDU skewing was detected."
    ::= { stpxBpduSkewingEntry  5 }

--
-- Multiple Spanning Tree Objects
--

stpxMSTMaxInstanceNumber  OBJECT-TYPE
    SYNTAX      Integer32 (1..256)
    MAX-ACCESS  read-only
    STATUS      deprecated
    DESCRIPTION
       "The maximum MST (Multiple Spanning Tree) instance id, 
       that can be supported by the device for Cisco proprietary
       implementation of the MST Protocol.

       This object is deprecated and replaced by 
       stpxSMSTMaxInstanceID."
    ::= { stpxMSTObjects 1}

stpxMSTRegionName OBJECT-TYPE
    SYNTAX      DisplayString (SIZE(0..32))  
    MAX-ACCESS  read-only
    STATUS      current
    DESCRIPTION
       "The operational MST region name."  
    ::= { stpxMSTObjects 2}

stpxMSTRegionRevision OBJECT-TYPE
    SYNTAX      Integer32 (1..65535) 
    MAX-ACCESS  read-only
    STATUS      deprecated
    DESCRIPTION
       "The operational MST region version.

       This object is deprecated and replaced by 
       stpxSMSTRegionRevision."  
    ::= { stpxMSTObjects 3 } 

stpxMSTInstanceTable OBJECT-TYPE
    SYNTAX      SEQUENCE OF StpxMSTInstanceEntry
    MAX-ACCESS  not-accessible
    STATUS      deprecated 
    DESCRIPTION
       "This table contains MST instance information with
       one entry for an MST instance within the range of 
       0 to the object value of stpxMSTMaxInstanceNumber. 
       
       This table is deprecated and replaced by 
       stpxSMSTInstanceTable." 
    ::= {stpxMSTObjects 4 }

stpxMSTInstanceEntry OBJECT-TYPE
    SYNTAX      StpxMSTInstanceEntry
    MAX-ACCESS  not-accessible
    STATUS      deprecated
    DESCRIPTION
       "A conceptual row containing the MST instance 
       information."
    INDEX  { stpxMSTInstanceIndex }
    ::= { stpxMSTInstanceTable 1 }

StpxMSTInstanceEntry ::= SEQUENCE {
    stpxMSTInstanceIndex Integer32,
    stpxMSTInstanceVlansMapped OCTET STRING,
    stpxMSTInstanceVlansMapped2k OCTET STRING,
    stpxMSTInstanceVlansMapped3k OCTET STRING,
    stpxMSTInstanceVlansMapped4k OCTET STRING,
    stpxMSTInstanceRemainingHopCount Integer32
}

stpxMSTInstanceIndex OBJECT-TYPE
    SYNTAX      Integer32 (0..256) 
    MAX-ACCESS  not-accessible
    STATUS      deprecated
    DESCRIPTION
       "An integer that uniquely identifies an MST instance 
       within the range of 0 to the object value of
       stpxMSTMaxInstanceNumber.

       This object is deprecated and replaced by 
       stpxSMSTInstanceIndex." 
    ::= {stpxMSTInstanceEntry 1 }

stpxMSTInstanceVlansMapped OBJECT-TYPE
    SYNTAX     OCTET STRING (SIZE (0..128))
    MAX-ACCESS read-only
    STATUS     deprecated
    DESCRIPTION
       "A string of octets containing one bit per VLAN. The
       first octet corresponds to VLANs with VlanIndex values
       of 0 through 7; the second octet to VLANs 8 through
       15; etc.  The most significant bit of each octet
       corresponds to the lowest value VlanIndex in that octet.

       For each VLAN, if it is mapped to this MST instance, 
       then the bit corresponding to that VLAN is set to '1'.

       This object is deprecated and replaced by 
       stpxSMSTInstanceVlansMapped1k2k."
    ::= {stpxMSTInstanceEntry 2 }

stpxMSTInstanceVlansMapped2k OBJECT-TYPE
    SYNTAX     OCTET STRING (SIZE (0..128))
    MAX-ACCESS read-only
    STATUS     deprecated
    DESCRIPTION
       "A string of octets containing one bit per VLAN for
        VLANS with VlanIndex values of 1024 through 2047. The
        first octet corresponds to VLANs with VlanIndex values
        of 1024 through 1031; the second octet to VLANs 1032
        through 1039; etc.  The most significant bit of each
        octet corresponds to the lowest value VlanIndex in that
        octet.

        For each VLAN, if it is mapped to this MST instance, 
        then the bit corresponding to that VLAN is set to '1'.

        This object is deprecated and replaced by 
       stpxSMSTInstanceVlansMapped1k2k."
    ::= {stpxMSTInstanceEntry 3 }

stpxMSTInstanceVlansMapped3k OBJECT-TYPE
    SYNTAX     OCTET STRING (SIZE (0..128))
    MAX-ACCESS read-only
    STATUS     deprecated
    DESCRIPTION
       "A string of octets containing one bit per VLAN for
       VLANS with VlanIndex values of 2048 through 3071. The
       first octet corresponds to VLANs with VlanIndex values
       of 2048 through 2055; the second octet to VLANs 2056
       through 2063; etc.  The most significant bit of each
       octet corresponds to the lowest value VlanIndex in that
       octet.

       For each VLAN, if it is mapped to this MST instance, 
       then the bit corresponding to that VLAN is set to '1'.

       This object is deprecated and replaced by 
       stpxSMSTInstanceVlansMapped3k4k."
    ::= {stpxMSTInstanceEntry 4 }

stpxMSTInstanceVlansMapped4k OBJECT-TYPE
    SYNTAX     OCTET STRING (SIZE (0..128))
    MAX-ACCESS read-only
    STATUS     deprecated
    DESCRIPTION
       "A string of octets containing one bit per VLAN for
       VLANS with VlanIndex values of 3072 through 4095. The
       first octet corresponds to VLANs with VlanIndex values
       of 3072 through 3079; the second octet to VLANs 3080
       through 3087; etc.  The most significant bit of each
       octet corresponds to the lowest value VlanIndex in that
       octet.

       For each VLAN, if it is mapped to this MST instance, 
       then the bit corresponding to that VLAN is set to '1'.

       This object is deprecated and replaced by
       stpxSMSTInstanceVlansMapped3k4k."
    ::= {stpxMSTInstanceEntry 5 }

stpxMSTInstanceRemainingHopCount OBJECT-TYPE
    SYNTAX     Integer32 (0..40)
    MAX-ACCESS read-only
    STATUS     deprecated
    DESCRIPTION
        "The remaining hop count for this MST instance.

        This object is only instantiated when the object value of
        stpxSpanningTreeType is mst(4).

        This object is deprecated and replaced by 
        stpxSMSTInstanceRemainingHopCount."
    ::= {stpxMSTInstanceEntry 6 }

stpxMSTRegionEditBufferStatus OBJECT-TYPE
    SYNTAX     INTEGER  {
                         released(1),
                         acquiredBySnmp(2),
                         acquiredByNonSnmp(3)
               }   
    MAX-ACCESS read-only
    STATUS     current
    DESCRIPTION
       "Indicates the current ownership status of the unique 
        Region Config Edit Buffer. 

        released -- the Edit Buffer can be acquired by any of 
                    the SNMP management stations. 

        acquiredBySnmp -- the Edit Buffer is acquired by
                    any of the SNMP management stations. 

        acquiredByNonSnmp -- the Edit Buffer is acquired by the 
                    non-SNMP users managing the device." 
    ::= { stpxMSTObjects 5 }

stpxMSTRegionEditBufferOperation OBJECT-TYPE
    SYNTAX     INTEGER  {
                         other(1), -- read-only
                         acquire(2),
                         releaseWithForce(3), 
                         commit(4),
                         rollBack(5)
               }   
    MAX-ACCESS read-write
    STATUS     current
    DESCRIPTION
            "Indicates the operation that is performed on the Region 
            Config Edit Buffer.

            other --   none of the following operations.  

            acquire -- acquire the Edit Buffer. This operation can 
                       only be performed when the object 
                       stpxMSTRegionEditBufferStatus has the value of
                       released(1). After the successful operation of 
                       this action, the stpxMSTRegionEditBufferStatus
                       will be changed to acquiredBySnmp(2). 
                        
            releaseWithForce -- release the Edit Buffer acquired by
                       non-SNMP users with force and discard the changes
                       in the Edit Buffer. This operation can only be 
                       performed when the object 
                       stpxMSTRegionEditBufferStatus has the value of 
                       acquiredByNonSnmp(2).

            commit --  commit the changes in the Edit Buffer
                       and release the Edit Buffer. The successful 
                       operation of this action will make the changes
                       in the Edit Buffer effective on the device.
                       This operation can only be performed when the 
                       object stpxMSTRegionEditBufferStatus has the 
                       value of acquiredBySnmp(3).
             
            rollBack -- discard the changes in the Edit Buffer
                       and release the Edit Buffer. This operation can 
                       only be performed when the object 
                       stpxMSTRegionEditBufferStatus has the value 
                       of acquiredBySnmp(3).

            This object always returns other(1) when it is read."  
    ::= { stpxMSTObjects 6 }


stpxMSTRegionEditName OBJECT-TYPE
    SYNTAX      DisplayString (SIZE(0..32))
    MAX-ACCESS  read-write
    STATUS      current
    DESCRIPTION
       "The MST region name in the Edit Buffer. 

       This object is only instantiated when the 
       stpxMSTRegionEditBufferStatus has the value of 
       acquiredBySnmp(2)."
     ::= { stpxMSTObjects 7 }

stpxMSTRegionEditRevision OBJECT-TYPE
    SYNTAX      Integer32 (1..65535)
    MAX-ACCESS  read-write
    STATUS      deprecated
    DESCRIPTION
       "The MST region version in the Edit Buffer. This object is
       only instantiated when the stpxMSTRegionEditBufferStatus 
       has the value of acquiredBySnmp(2).

       This object is deprecated and replaced by
       stpxSMSTRegionEditRevision."
     ::= { stpxMSTObjects 8 }

stpxMSTInstanceEditTable OBJECT-TYPE
    SYNTAX      SEQUENCE OF StpxMSTInstanceEditEntry
    MAX-ACCESS  not-accessible
    STATUS      deprecated
    DESCRIPTION
       "This table contains MST instance information in the 
       Edit Buffer with one entry for each MST
       instance numbered from 0 to stpxMSTMaxInstanceNumber. 

       This table is only instantiated when the 
       stpxMSTRegionEditBufferStatus has the value of
       acquiredBySnmp(2).

       This table is deprecated and replaced by 
       stpxSMSTInstanceEditTable."
     ::= { stpxMSTObjects 9 }

stpxMSTInstanceEditEntry OBJECT-TYPE
    SYNTAX      StpxMSTInstanceEditEntry
    MAX-ACCESS  not-accessible
    STATUS      deprecated
    DESCRIPTION
       "A conceptual row containing MST instance information 
       in the Edit Buffer."
    INDEX  { stpxMSTInstanceEditIndex }
    ::= { stpxMSTInstanceEditTable 1 }

StpxMSTInstanceEditEntry ::= SEQUENCE {
    stpxMSTInstanceEditIndex  Integer32,
    stpxMSTInstanceEditVlansMap OCTET STRING,
    stpxMSTInstanceEditVlansMap2k OCTET STRING,
    stpxMSTInstanceEditVlansMap3k OCTET STRING,
    stpxMSTInstanceEditVlansMap4k OCTET STRING
}

stpxMSTInstanceEditIndex OBJECT-TYPE
    SYNTAX      Integer32 (0..256) 
    MAX-ACCESS  not-accessible
    STATUS      deprecated
    DESCRIPTION
       "An integer that uniquely identifies an MST instance 
       from 0 to the object value of stpxMSTMaxInstanceNumber.

       The instances of this table entry with 
       stpxMSTInstanceEditIndex of zero can not be 
       modified.

       This object is deprecated and replaced by 
       stpxSMSTInstanceEditIndex."
    ::= {stpxMSTInstanceEditEntry 1 }

stpxMSTInstanceEditVlansMap OBJECT-TYPE
    SYNTAX     OCTET STRING (SIZE (0..128))
    MAX-ACCESS read-write
    STATUS     deprecated
    DESCRIPTION
       "A string of octets containing one bit per VLAN. The
       first octet corresponds to VLANs with VlanIndex values
       of 0 through 7; the second octet to VLANs 8 through
       15; etc.  The most significant bit of each octet
       corresponds to the lowest value VlanIndex in that octet.

       For each VLAN, if it is mapped to this MST instance, 
       then the bit corresponding to that VLAN is set to 
       '1'. Each VLAN can only be mapped to one unique MST 
       instance in the range from 1 to stpxMSTMaxInstanceNumber.
       If the bit corresponding to a VLAN is changed from '1' 
       to '0', then that VLAN will be automatically mapped to 
       MST instance 0 by the device.

       This object is deprecated and replaced by 
       stpxSMSTInstanceEditVlansMap1k2k."
    ::= {stpxMSTInstanceEditEntry 2 }

stpxMSTInstanceEditVlansMap2k OBJECT-TYPE
    SYNTAX     OCTET STRING (SIZE (0..128))
    MAX-ACCESS read-write
    STATUS     deprecated
    DESCRIPTION
       "A string of octets containing one bit per VLAN for
       VLANS with VlanIndex values of 1024 through 2047. The
       first octet corresponds to VLANs with VlanIndex values
       of 1024 through 1031; the second octet to VLANs 1032
       through 1039; etc.  The most significant bit of each
       octet corresponds to the lowest value VlanIndex in that
       octet.

       For each VLAN, if it is mapped to this MST instance,
       then the bit corresponding to that VLAN is set to
       '1'. Each VLAN can only be mapped to one unique MST
       instance in the range from 1 to stpxMSTMaxInstanceNumber.
       If the bit corresponding to a VLAN is changed from '1' 
       to '0', then that VLAN will be automatically mapped to 
       MST instance 0 by the device.

       This object is deprecated and replaced by 
       stpxSMSTInstanceEditVlansMap1k2k."
    ::= {stpxMSTInstanceEditEntry 3 }

stpxMSTInstanceEditVlansMap3k OBJECT-TYPE
    SYNTAX     OCTET STRING (SIZE (0..128))
    MAX-ACCESS read-write
    STATUS     deprecated
    DESCRIPTION
       "A string of octets containing one bit per VLAN for
        VLANS with VlanIndex values of 2048 through 3071. The
        first octet corresponds to VLANs with VlanIndex values
        of 2048 through 2055; the second octet to VLANs 2056
        through 2063; etc.  The most significant bit of each
        octet corresponds to the lowest value VlanIndex in that
        octet.

        For each VLAN, if it is mapped to this MST instance,
        then the bit corresponding to that VLAN is set to
        '1'. Each VLAN can only be mapped to one unique MST
        instance in the range from 1 to stpxMSTMaxInstanceNumber.
        If the bit corresponding to a VLAN is changed from '1' 
        to '0', then that VLAN will be automatically mapped to 
        MST instance 0 by the device.

        This object is deprecated and replaced by 
        stpxSMSTInstanceEditVlansMap3k4k."
    ::= {stpxMSTInstanceEditEntry 4 }

stpxMSTInstanceEditVlansMap4k OBJECT-TYPE
    SYNTAX     OCTET STRING (SIZE (0..128))
    MAX-ACCESS read-write
    STATUS     deprecated
    DESCRIPTION
       "A string of octets containing one bit per VLAN for
       VLANS with VlanIndex values of 3072 through 4095. The
       first octet corresponds to VLANs with VlanIndex values
       of 3072 through 3079; the second octet to VLANs 3080
       through 3087; etc.  The most significant bit of each
       octet corresponds to the lowest value VlanIndex in that
       octet.

       For each VLAN, if it is mapped to this MST instance,
       then the bit corresponding to that VLAN is set to
       '1'. Each VLAN can only be mapped to one unique MST
       instance in the range from 1 to stpxMSTMaxInstanceNumber.
       If the bit corresponding to a VLAN is changed from '1' 
       to '0', then that VLAN will be automatically mapped to 
       MST instance 0 by the device.

       This object is deprecated and replaced by
       stpxSMSTInstanceEditVlansMap3k4k."
    ::= {stpxMSTInstanceEditEntry 5 }


stpxPreferredMSTInstancesTable OBJECT-TYPE
    SYNTAX     SEQUENCE OF StpxPreferredMSTInstancesEntry
    MAX-ACCESS not-accessible
    STATUS     deprecated
    DESCRIPTION
       "The table containing indications of which MST instances 
       are preferred on which  trunk ports.  The preferred
       MST instances on a trunk port have a lower Path Cost value
       compared with the MST instances on the trunk not in the
       preferred list." 
    ::= { stpxMSTObjects 10 }

stpxPreferredMSTInstancesEntry OBJECT-TYPE
    SYNTAX     StpxPreferredMSTInstancesEntry
    MAX-ACCESS not-accessible
    STATUS     deprecated
    DESCRIPTION
       "An entry indicating which MST instances are preferred on 
       a specific trunk port."
    AUGMENTS   { vlanTrunkPortEntry }
    ::= { stpxPreferredMSTInstancesTable 1 }

StpxPreferredMSTInstancesEntry ::= SEQUENCE {
    stpxPreferredMSTInstancesMap      OCTET STRING
}

stpxPreferredMSTInstancesMap OBJECT-TYPE
    SYNTAX     OCTET STRING(SIZE(1..32))
    MAX-ACCESS read-write
    STATUS     deprecated
    DESCRIPTION
       "A string of octets containing one bit per MST instances 
       on this trunk port.  The first octet corresponds to MST 
       instances of 0 through 7; the second octet to MST instances 
       8 through 15; etc. The most significant bit of each octet 
       corresponds to the lowest MST instance value in that octet. 
       The number of bits for this mib object will be determined 
       by the value of stpxMSTMaxInstanceNumber.

       For each instance, if it is preferred on this trunk port, 
       then the bit corresponding to that instance is set to '1'."
    ::= { stpxPreferredMSTInstancesEntry 1 }

stpxMSTPortTable OBJECT-TYPE
    SYNTAX      SEQUENCE OF StpxMSTPortEntry
    MAX-ACCESS  not-accessible
    STATUS      deprecated 
    DESCRIPTION
       "A table containing port information for the MST 
        Protocol on all the bridge ports existing on the 
        system."

    ::= { stpxMSTObjects 11 }

stpxMSTPortEntry OBJECT-TYPE
    SYNTAX      StpxMSTPortEntry
    MAX-ACCESS  not-accessible
    STATUS      deprecated 
    DESCRIPTION
                "An entry with port information for the MST Protocol
                on a bridge port."
    INDEX { stpxMSTPortIndex }
    ::= { stpxMSTPortTable 1 }

StpxMSTPortEntry ::= SEQUENCE {
    stpxMSTPortIndex Integer32,
    stpxMSTPortAdminLinkType INTEGER,
    stpxMSTPortOperLinkType INTEGER,
    stpxMSTPortProtocolMigration TruthValue,
    stpxMSTPortStatus BITS
}

stpxMSTPortIndex OBJECT-TYPE
    SYNTAX      Integer32 (1..65535)
    MAX-ACCESS  not-accessible
    STATUS      deprecated 
    DESCRIPTION
       "The value of dot1dBasePort (i.e. dot1dBridge.1.4)
        for the bridge port."
    REFERENCE
       "dot1dBasePort is defined in RFC1493."
    ::= { stpxMSTPortEntry 1 }

stpxMSTPortAdminLinkType OBJECT-TYPE
    SYNTAX     INTEGER {
                        pointToPoint(1),
                        shared(2),
                        auto(3) 
               }
    MAX-ACCESS read-write
    STATUS     deprecated 
    DESCRIPTION
       "Indicates the administrative link type configuration of 
       a bridge port for the MST protocol. 

       pointToPoint -- the port is administratively configured to
               be connected to a point-to-point link.

       shared -- the port is administratively configured to be
               connected to a shared medium. 

       auto -- the administrative configuration of the port's 
               link type depends on link duplex of the port.
               If the port link is full-duplex, the administrative 
               link type configuration on this port will be taken 
               as pointTopoint(1). If the port link is half-duplex, 
               the administrative link type configuration on this
               port will be taken as shared(2).

       This configuration of this object only takes effect when the
       stpxSpanningTreeType is mst(4) or rapidPvstPlus(5).
       stpxMSTPortAdminLinkType is deprecated and replaced 
       with stpxRSTPPortAdminLinkType."
    DEFVAL { auto } 
    ::= { stpxMSTPortEntry 2 }

stpxMSTPortOperLinkType OBJECT-TYPE
    SYNTAX     INTEGER {
                        pointToPoint(1),
                        shared(2),
                        other(3)
               }
    MAX-ACCESS read-only
    STATUS     deprecated 
    DESCRIPTION
       "Indicates the operational link type of a bridge port
       for the MST protocol.

       pointToPoint -- the port is operationally connected to
               a point-to-point link.

       shared -- the port is operationally connected to 
               a shared medium.

       other -- none of the above.
 
       This object is only instantiated when the object value of
       stpxSpanningTreeType is mst(4).  stpxMSTPortOperLinkType 
       is deprecated and replaced with stpxRSTPPortOperLinkType."
    ::= { stpxMSTPortEntry 3 }

stpxMSTPortProtocolMigration OBJECT-TYPE
    SYNTAX     TruthValue
    MAX-ACCESS read-write
    STATUS     deprecated
    DESCRIPTION
       "The protocol migration control on this port. When the 
       object value of  stpxSpanningTreeType is mst(4) or 
       rapidPvstPlus(5), setting true(1) to this object forces 
       the device to try using version 2 BPDUs on this port. 
       When the object value of stpxSpanningTreeType is neither 
       mst(4) nor rapidPvstPlus(5), setting true(1) to this 
       object has no effect. Setting false(2) to this object has 
       no effect. This object always returns false(2) when read.
       stpxMSTPortProtocolMigration is deprecated and 
       replaced with stpxRSTPPortProtocolMigration."
    REFERENCE 
       "IEEE 802.1w clause 14.8.2.4, 17.26."
    ::= { stpxMSTPortEntry 4 }

stpxMSTPortStatus OBJECT-TYPE
    SYNTAX     BITS {
                     edge(0),
                     boundary(1),
                     pvst(2),
                     stp(3) 
               }
    MAX-ACCESS read-only
    STATUS     deprecated 
    DESCRIPTION
       "Indicates the operational status of the port for the 
       MST protocol. 

       edge -- this port is an edge port for the MST region.

       boundary -- this port is a boundary port for the 
               MST region.

       pvst --  this port is connected to a PVST/PVST+ bridge.   
 
       stp -- this port is connected to a Single Spanning
               Tree bridge. 
  
       This object is only instantiated when the object value
       of stpxSpanningTreeType is mst(4).

       This object is deprecated and replaced by 
       stpxSMSTPortStatus."
   ::= { stpxMSTPortEntry 5 }

stpxMSTPortRoleTable OBJECT-TYPE
    SYNTAX      SEQUENCE OF StpxMSTPortRoleEntry
    MAX-ACCESS  not-accessible
    STATUS      deprecated 
    DESCRIPTION
       "A table containing a list of the bridge ports for a 
       particular MST instance.  This table is only instantiated 
       when the stpxSpanningTreeType is mst(4). 

       This table is deprecated and replaced with 
       stpxRSTPPortRoleTable."  
    ::= { stpxMSTObjects 12 }

stpxMSTPortRoleEntry OBJECT-TYPE
    SYNTAX      StpxMSTPortRoleEntry
    MAX-ACCESS  not-accessible
    STATUS      deprecated 
    DESCRIPTION
       "An entry containing the port role information for the MST
       protocol on a port for a particular MST instance existing
       on the system." 
    INDEX { stpxMSTPortRoleInstanceIndex, 
            stpxMSTPortRolePortIndex }
    ::= { stpxMSTPortRoleTable 1 }

StpxMSTPortRoleEntry ::= SEQUENCE {
    stpxMSTPortRoleInstanceIndex Integer32,
    stpxMSTPortRolePortIndex Integer32,
    stpxMSTPortRoleValue     INTEGER 
}

stpxMSTPortRoleInstanceIndex OBJECT-TYPE
    SYNTAX      Integer32 (0..256)
    MAX-ACCESS  not-accessible
    STATUS      deprecated 
    DESCRIPTION
       "The MST instance id within the range of 0 to
       stpxMSTMaxInstanceNumber."
    ::= { stpxMSTPortRoleEntry 1 }

stpxMSTPortRolePortIndex OBJECT-TYPE
    SYNTAX      Integer32 (1..65535)
    MAX-ACCESS  not-accessible
    STATUS      deprecated 
    DESCRIPTION
       "The value of dot1dBasePort (i.e. dot1dBridge.1.4)
       for the bridge port."
    REFERENCE
       "dot1dBasePort is defined in RFC1493."
    ::= { stpxMSTPortRoleEntry 2 }

stpxMSTPortRoleValue OBJECT-TYPE
    SYNTAX      INTEGER {
                         disabled(1), 
                         root(2),
                         designated(3),
                         alternate(4),
                         backUp(5),
                         boundary(6),
                         master(7)
                }
    MAX-ACCESS  read-only
    STATUS      deprecated 
    DESCRIPTION
       "Indicates the port role on a particular MST instance
       for the MST protocol. 

       disabled --  this port has no role on this MST instance. 

       root -- this port has the role of root port on this MST
                   instance. 

       designated -- this port has the role of designated 
                   port on this MST instance.

       alternate -- this port has the role of alternate port
                   on this MST instance.

       backUp -- this port has the role of backup port on this  
                   MST instance.

       boundary -- this port has the role of boundary port on 
                   this MST instance.

       master -- this port has the role of master port on
                 this MST instance."
    ::= { stpxMSTPortRoleEntry  3 }

stpxMSTMaxHopCount OBJECT-TYPE
    SYNTAX      Integer32 (1..40)
    MAX-ACCESS  read-write
    STATUS      current
    DESCRIPTION
        "The maximum number of hops for the MST region."
    DEFVAL { 20 }
    ::= { stpxMSTObjects 13 }

--
-- Rapid Spanning Tree Protocol Objects
--

stpxRSTPPortTable OBJECT-TYPE
    SYNTAX      SEQUENCE OF StpxRSTPPortEntry
    MAX-ACCESS  not-accessible
    STATUS      current
    DESCRIPTION
       "A table containing port information for the RSTP 
        Protocol on all the bridge ports existing in the 
        system."
    ::= { stpxRSTPObjects 1 }

stpxRSTPPortEntry OBJECT-TYPE
    SYNTAX      StpxRSTPPortEntry
    MAX-ACCESS  not-accessible
    STATUS      current
    DESCRIPTION
                "An entry with port information for the RSTP Protocol
                on a bridge port."
    INDEX { stpxRSTPPortIndex }
    ::= { stpxRSTPPortTable 1 }

StpxRSTPPortEntry ::= SEQUENCE {
    stpxRSTPPortIndex Integer32,
    stpxRSTPPortAdminLinkType INTEGER,
    stpxRSTPPortOperLinkType INTEGER,
    stpxRSTPPortProtocolMigration TruthValue
}

stpxRSTPPortIndex OBJECT-TYPE
    SYNTAX      Integer32 (1..65535)
    MAX-ACCESS  not-accessible
    STATUS      current
    DESCRIPTION
       "The value of dot1dBasePort (i.e. dot1dBridge.1.4)
        for the bridge port."
    REFERENCE
       "dot1dBasePort is defined in RFC1493."
    ::= { stpxRSTPPortEntry 1 }

stpxRSTPPortAdminLinkType OBJECT-TYPE
    SYNTAX     INTEGER {
                        pointToPoint(1),
                        shared(2),
                        auto(3) 
               }
    MAX-ACCESS read-write
    STATUS     current
    DESCRIPTION
       "Indicates the administrative link type configuration of 
       a bridge port for the RSTP protocol. 

       pointToPoint -- the port is administratively configured to
               be connected to a point-to-point link.

       shared -- the port is administratively configured to be
               connected to a shared medium. 

       auto -- the administrative configuration of the port's 
               link type depends on link duplex of the port.
               If the port link is full-duplex, the administrative 
               link type configuration on this port will be taken 
               as pointTopoint(1). If the port link is half-duplex, 
               the administrative link type configuration on this
               port will be taken as shared(2).

       This configuration of this object only takes effect when the
       stpxSpanningTreeType is mst(4) or rapidPvstPlus(5)." 
    DEFVAL { auto } 
    ::= { stpxRSTPPortEntry 2 }

stpxRSTPPortOperLinkType OBJECT-TYPE
    SYNTAX     INTEGER {
                        pointToPoint(1),
                        shared(2),
                        other(3)
               }
    MAX-ACCESS read-only
    STATUS     current
    DESCRIPTION
       "Indicates the operational link type of a bridge port
       for the RSTP protocol.

       pointToPoint -- the port is operationally connected to
               a point-to-point link.

       shared -- the port is operationally connected to 
               a shared medium.

       other -- none of the above.
 
       This object is only instantiated when the object value of
       stpxSpanningTreeType is mst(4) or rapidPvstPlus(5)." 
    ::= { stpxRSTPPortEntry 3 }

stpxRSTPPortProtocolMigration OBJECT-TYPE
    SYNTAX     TruthValue
    MAX-ACCESS read-write
    STATUS     current
    DESCRIPTION
       "The protocol migration control on this port. When the 
       object value of  stpxSpanningTreeType is mst(4) or 
       rapidPvstPlus(5), setting true(1) to this object forces 
       the device to try using version 2 BPDUs on this port. 
       When the object value of stpxSpanningTreeType is neither 
       mst(4) nor rapidPvstPlus(5), setting true(1) to 
       this object has no effect. Setting false(2) to this 
       object has no effect. This object always returns 
       false(2) when read."
    REFERENCE 
       "IEEE 802.1w clause 14.8.2.4, 17.26."
    ::= { stpxRSTPPortEntry 4 }


stpxRSTPPortRoleTable OBJECT-TYPE
    SYNTAX      SEQUENCE OF StpxRSTPPortRoleEntry
    MAX-ACCESS  not-accessible
    STATUS      current
    DESCRIPTION
       "A table containing a list of the bridge ports for a 
       particular Spanning Tree instance.  This table is 
       only instantiated when the stpxSpanningTreeType is mst(4) 
       or rapidPvstPlus(5)."  
    ::= { stpxRSTPObjects 2 }

stpxRSTPPortRoleEntry OBJECT-TYPE
    SYNTAX      StpxRSTPPortRoleEntry
    MAX-ACCESS  not-accessible
    STATUS      current
    DESCRIPTION
       "An entry containing the port role information for the RSTP
       protocol on a port for a particular Spanning Tree instance." 
    INDEX { stpxRSTPPortRoleInstanceIndex, 
            stpxRSTPPortRolePortIndex }
    ::= { stpxRSTPPortRoleTable 1 }

StpxRSTPPortRoleEntry ::= SEQUENCE {
    stpxRSTPPortRoleInstanceIndex Integer32,
    stpxRSTPPortRolePortIndex Integer32,
    stpxRSTPPortRoleValue     INTEGER 
}

stpxRSTPPortRoleInstanceIndex OBJECT-TYPE
    SYNTAX      Integer32 (0..4095)
    MAX-ACCESS  not-accessible
    STATUS      current
    DESCRIPTION
       "The Spanning Tree instance id, it can either be a 
       VLAN number if the stpxSpanningTreeType is rapidPvstPlus(5) 
       or an MST instance id if the stpxSpanningTreeType is mst(4)."
    ::= { stpxRSTPPortRoleEntry 1 }

stpxRSTPPortRolePortIndex OBJECT-TYPE
    SYNTAX      Integer32 (1..65535)
    MAX-ACCESS  not-accessible
    STATUS      current
    DESCRIPTION
       "The value of dot1dBasePort (i.e. dot1dBridge.1.4)
       for the bridge port."
    REFERENCE
       "dot1dBasePort is defined in RFC1493."
    ::= { stpxRSTPPortRoleEntry 2 }

stpxRSTPPortRoleValue OBJECT-TYPE
    SYNTAX      INTEGER {
                         disabled(1), 
                         root(2),
                         designated(3),
                         alternate(4),
                         backUp(5),
                         boundary(6),
                         master(7)
                }
    MAX-ACCESS  read-only
    STATUS      current
    DESCRIPTION
       "Indicates the port role on a particular Spanning Tree 
       instance for the RSTP protocol. 

       disabled --  this port has no role in this Spanning
                   Tree instance. 

       root -- this port has the role of root port in this
                   Spanning Tree instance. 

       designated -- this port has the role of designated 
                   port in this Spanning Tree instance.

       alternate -- this port has the role of alternate port
                   in this Spanning Tree instance.

       backUp -- this port has the role of backup port in this  
                   Spanning Tree instance.

       boundary -- this port has the role of boundary port in 
                   this Spanning Tree instance.

       master -- this port has the role of master port in
                   this Spanning Tree instance.

       This object could have a value of 'boundary' or 'master'
       only when the object value of stpxSpanningTreeType is mst(4)." 
    ::= { stpxRSTPPortRoleEntry  3 }

--
-- Rapid PVST+ Objects
--
stpxRPVSTPortTable OBJECT-TYPE
    SYNTAX      SEQUENCE OF StpxRPVSTPortEntry
    MAX-ACCESS  not-accessible
    STATUS      current
    DESCRIPTION
       "A table containing a list of the bridge ports 
        for a particular Spanning Tree Instance.
        This table is only instantiated when the object value
        of stpxSpanningTreeType is rapidPvstPlus(5)."
    ::= { stpxRPVSTObjects 1 }

stpxRPVSTPortEntry OBJECT-TYPE
    SYNTAX      StpxRPVSTPortEntry
    MAX-ACCESS  not-accessible
    STATUS      current
    DESCRIPTION
                "An entry with port status information on a 
                 bridge port for a particular Spanning Tree 
                 Instance."
    INDEX { stpxRPVSTPortVlanIndex,
            stpxRPVSTPortIndex }
    ::= { stpxRPVSTPortTable 1 }

StpxRPVSTPortEntry ::= SEQUENCE {
    stpxRPVSTPortVlanIndex  VlanIndex,
    stpxRPVSTPortIndex Integer32,
    stpxRPVSTPortStatus BITS
}
stpxRPVSTPortVlanIndex OBJECT-TYPE
    SYNTAX      VlanIndex
    MAX-ACCESS  not-accessible
    STATUS      current
    DESCRIPTION
             "The VLAN id of the VLAN."
    ::= { stpxRPVSTPortEntry 1 }

stpxRPVSTPortIndex OBJECT-TYPE
    SYNTAX      Integer32 (1..65535)
    MAX-ACCESS  not-accessible
    STATUS      current
    DESCRIPTION
       "The value of dot1dBasePort (i.e. dot1dBridge.1.4)
        for the bridge port."
    REFERENCE
       "dot1dBasePort is defined in RFC1493."
    ::= { stpxRPVSTPortEntry 2 }

stpxRPVSTPortStatus OBJECT-TYPE
    SYNTAX     BITS {
                     edge(0),
                     unused1(1),
                     unused2(2),
                     stp(3) 
               }
    MAX-ACCESS read-only
    STATUS     current
    DESCRIPTION
       "Indicates the operational status of the port for the 
        Rapid PVST+ protocol.

       edge -- this port is an edge port for the RST region.

       unused1 -- unused bit 1.

       unused2 -- unused bit 2.

       stp -- this port is connected to a Single Spanning
               Tree/PVST+ bridge." 
  
   ::= { stpxRPVSTPortEntry 3 }

--
-- Standard Multiple Spanning Tree Objects.
-- This group of objects is for the management
-- of IEEE Multiple Spanning Tree, i.e., Standard MST
-- (SMST). Objects in this group replace some of the
-- objects in stpxMSTObjects which are for the the 
-- managment of the Cisco proprietary implementation
-- of the Multiple Spanning Tree (MST).
--

stpxSMSTMaxInstances  OBJECT-TYPE
    SYNTAX      Unsigned32
    MAX-ACCESS  read-only
    STATUS      current
    DESCRIPTION
       "The maximum number of MST instances that can be 
       supported by the device for IEEE MST." 
    ::= { stpxSMSTObjects 1 }

stpxSMSTMaxInstanceID OBJECT-TYPE
    SYNTAX      Unsigned32
    MAX-ACCESS  read-only
    STATUS      current
    DESCRIPTION
       "The maximum MST instance ID that can be supported 
       by the device for IEEE MST." 
    ::= { stpxSMSTObjects 2 }

stpxSMSTRegionRevision OBJECT-TYPE  
    SYNTAX      Unsigned32
    MAX-ACCESS  read-only
    STATUS      current
    DESCRIPTION
       "The operational region version for IEEE MST."
    ::= { stpxSMSTObjects 3 }

stpxSMSTRegionEditRevision OBJECT-TYPE
    SYNTAX      Unsigned32  
    MAX-ACCESS  read-write
    STATUS      current
    DESCRIPTION
       "The MST region version in the Edit Buffer for IEEE 
       MST.

       This object is only instantiated when the 
       stpxMSTRegionEditBufferStatus has the value of 
       acquiredBySnmp(2)."
     ::= { stpxSMSTObjects 4 }

stpxSMSTInstanceTable OBJECT-TYPE
    SYNTAX      SEQUENCE OF StpxSMSTInstanceEntry
    MAX-ACCESS  not-accessible
    STATUS      current
    DESCRIPTION
       "This table contains MST instance information
       for IEEE MST."
    ::= {stpxSMSTObjects 5 }

stpxSMSTInstanceEntry OBJECT-TYPE
    SYNTAX      StpxSMSTInstanceEntry
    MAX-ACCESS  not-accessible
    STATUS      current
    DESCRIPTION
       "A conceptual row containing the MST instance 
       information for IEEE MST."
    INDEX  { stpxSMSTInstanceIndex }
    ::= { stpxSMSTInstanceTable 1 }

StpxSMSTInstanceEntry ::= SEQUENCE {
    stpxSMSTInstanceIndex Unsigned32,
    stpxSMSTInstanceVlansMapped1k2k OCTET STRING,
    stpxSMSTInstanceVlansMapped3k4k OCTET STRING,
    stpxSMSTInstanceRemainingHopCount Integer32,
    stpxSMSTInstanceCISTRegionalRoot OCTET STRING,
    stpxSMSTInstanceCISTIntRootCost Unsigned32
}

stpxSMSTInstanceIndex OBJECT-TYPE
    SYNTAX      Unsigned32
    MAX-ACCESS  not-accessible
    STATUS      current
    DESCRIPTION
       "The MST instance ID, the value of which is in the range 
       from 0 to stpxSMSTMaxInstanceID."
    ::= {stpxSMSTInstanceEntry 1 }

stpxSMSTInstanceVlansMapped1k2k OBJECT-TYPE
    SYNTAX     OCTET STRING (SIZE (0..256))
    MAX-ACCESS read-only
    STATUS     current
    DESCRIPTION
       "A string of octets containing one bit per VLAN for
       VLANS with VlanIndex values of 0 through 2047. The
       first octet corresponds to VLANs with VlanIndex values
       of 0 through 7; the second octet to VLANs 8 through
       15; etc.  The most significant bit of each octet
       corresponds to the lowest value VlanIndex in that octet.

       For each VLAN, if it is mapped to this MST instance,
       then the bit corresponding to that VLAN is set to '1'.
       If the length of this string is less than 256 octets,
       any 'missing' octets are assumed to contain the value 
       of zero."
    ::= {stpxSMSTInstanceEntry 2 }

stpxSMSTInstanceVlansMapped3k4k OBJECT-TYPE
    SYNTAX     OCTET STRING (SIZE (0..256))
    MAX-ACCESS read-only
    STATUS     current
    DESCRIPTION
       "A string of octets containing one bit per VLAN for
       VLANS with VlanIndex values of 2048 through 4095. The
       first octet corresponds to VLANs with VlanIndex values
       of 2048 through 2055; the second octet to VLANs 2056
       through 2063; etc.  The most significant bit of each
       octet corresponds to the lowest value VlanIndex in that
       octet.

       For each VLAN, if it is mapped to this MST instance,
       then the bit corresponding to that VLAN is set to '1'.
       If the length of this string is less than 256 octets,
       any 'missing' octets are assumed to contain the value 
       of zero."
    ::= {stpxSMSTInstanceEntry 3 }

stpxSMSTInstanceRemainingHopCount OBJECT-TYPE
    SYNTAX     Integer32 (-1..2147483647)  
    MAX-ACCESS read-only
    STATUS     current
    DESCRIPTION
        "The remaining hop count for this MST instance. If this object
        value is not applicable on an MST instance, then the value
        retrieved for this object for that MST instance will be -1. 

        This object is only instantiated when the object value of
        stpxSpanningTreeType is mst(4)."
    ::= {stpxSMSTInstanceEntry 4 }

stpxSMSTInstanceCISTRegionalRoot OBJECT-TYPE
    SYNTAX  OCTET STRING (SIZE (8)) 
    MAX-ACCESS  read-only
    STATUS  current
    DESCRIPTION
            "Indicates the Bridge Identifier (refer to BridgeId 
            defined in BRIDGE-MIB) of CIST (Common and Internal 
            Spanning Tree) Regional Root for the MST region.

            This object is only instantiated when the object value of
            stpxSpanningTreeType is mst(4) and stpxSMSTInstanceIndex
            is 0." 
    REFERENCE
            "IEEE 802.1S-2002: Section 13.9."
    ::= { stpxSMSTInstanceEntry 5 }

stpxSMSTInstanceCISTIntRootCost OBJECT-TYPE
    SYNTAX  Unsigned32
    MAX-ACCESS  read-only
    STATUS  current
    DESCRIPTION
            "Indicates the CIST Internal Root Path Cost, i.e., the
            path cost to the CIST Regional Root as specified by the
            corresponding stpxSMSTInstanceCISTRegionalRoot for the 
            MST region.

            This object is only instantiated when the object value of
            stpxSpanningTreeType is mst(4) and stpxSMSTInstanceIndex
            is 0." 
    REFERENCE 
            "IEEE 802.1S-2002: Section 13.9."
    ::= { stpxSMSTInstanceEntry 6 }

stpxSMSTInstanceEditTable OBJECT-TYPE
    SYNTAX      SEQUENCE OF StpxSMSTInstanceEditEntry
    MAX-ACCESS  not-accessible
    STATUS      current
    DESCRIPTION
       "This table contains MST instance information in the 
       Edit Buffer. 

       This table is only instantiated when the object value
       of  stpxMSTRegionEditBufferStatus has the value of
       acquiredBySnmp(2)."
     ::= { stpxSMSTObjects 6 }

stpxSMSTInstanceEditEntry OBJECT-TYPE
    SYNTAX      StpxSMSTInstanceEditEntry
    MAX-ACCESS  not-accessible
    STATUS      current
    DESCRIPTION
       "A conceptual row containing MST instance information 
       in the Edit Buffer.

       The total number of entries in this table has to be 
       less or equal to the object value of stpxSMSTMaxInstances."
    INDEX  { stpxSMSTInstanceEditIndex }
    ::= { stpxSMSTInstanceEditTable 1 }

StpxSMSTInstanceEditEntry ::= SEQUENCE {
    stpxSMSTInstanceEditIndex  Unsigned32,
    stpxSMSTInstanceEditVlansMap1k2k OCTET STRING,
    stpxSMSTInstanceEditVlansMap3k4k OCTET STRING,
    stpxSMSTInstanceEditRowStatus RowStatus
}

stpxSMSTInstanceEditIndex OBJECT-TYPE
    SYNTAX      Unsigned32
    MAX-ACCESS  not-accessible
    STATUS      current
    DESCRIPTION
       "The MST instance ID, the value of which is in the range from
       0 to stpxSMSTMaxInstanceID. 

       The instances of this table entry with 
       stpxSMSTInstanceEditIndex of zero is automatically
       created by the device and can not modified."
    ::= {stpxSMSTInstanceEditEntry 1 }

stpxSMSTInstanceEditVlansMap1k2k OBJECT-TYPE
    SYNTAX     OCTET STRING (SIZE (0..256))
    MAX-ACCESS read-create
    STATUS     current
    DESCRIPTION
       "A string of octets containing one bit per VLAN for
       VLANS with VlanIndex values of 0 through 2047. The
       first octet corresponds to VLANs with VlanIndex values
       of 0 through 7; the second octet to VLANs 8 through
       15; etc.  The most significant bit of each octet
       corresponds to the lowest value VlanIndex in that octet.

       For each VLAN, if it is mapped to this MST instance, 
       then the bit corresponding to that VLAN is set to 
       '1'. Each VLAN can only be mapped to one unique MST 
       instance with the range from 0 to stpxSMSTMaxInstanceNumber.
       If the bit corresponding to a VLAN is changed from '1' 
       to '0', then that VLAN will be automatically mapped to 
       SMST instance 0 by the device. If the bit corresponding 
       to a VLAN is changed from '0' to '1', then that VLAN will 
       be automatically removed from the MST instance this VLAN was 
       previously mapped to. If the length of this string is 
       less than 256 octets, any 'missing' octets are assumed to 
       contain the value of zero."
    ::= {stpxSMSTInstanceEditEntry 2 } 

stpxSMSTInstanceEditVlansMap3k4k OBJECT-TYPE
    SYNTAX     OCTET STRING (SIZE (0..256))
    MAX-ACCESS read-create
    STATUS     current
    DESCRIPTION
       "A string of octets containing one bit per VLAN for
       VLANS with VlanIndex values of 2048 through 4095. The
       first octet corresponds to VLANs with VlanIndex values
       of 2048 through 2055; the second octet to VLANs 2056 through
       2063; etc.  The most significant bit of each octet
       corresponds to the lowest value VlanIndex in that octet.

       For each VLAN, if it is mapped to this MST instance,
       then the bit corresponding to that VLAN is set to
       '1'. Each VLAN can only be mapped to one unique MST
       instance with the range from 0 to stpxSMSTMaxInstanceNumber.
       If the bit corresponding to a VLAN is changed from '1'
       to '0', then that VLAN will be automatically mapped to
       SMST instance 0 by the device. If the bit corresponding
       to a VLAN is changed from '0' to '1', then that VLAN will
       be automatically removed from the MST instance this VLAN was
       previously mapped to. If the length of this string is 
       less than 256 octets, any 'missing' octets are assumed to 
       contain the value of zero."
    ::= {stpxSMSTInstanceEditEntry 3 }

stpxSMSTInstanceEditRowStatus OBJECT-TYPE
    SYNTAX     RowStatus
    MAX-ACCESS read-create
    STATUS     current
    DESCRIPTION
       "This object controls the creation and deletion of a row 
       in stpxSMSTInstanceEditTable.

       When creating an entry in this table, 'createAndGo' method
       is used and the value of this object is set to 'active'.
       Deactivation of an 'active' entry is not allowed.  When 
       deleting an entry in this table, 'destroy' method is used. 
       Once a row becomes active, value in any other column 
       within such a row may be modified. When a row is active, 
       setting the instance of stpxSMSTInstanceEditVlansMap1k2k
       stpxSMSTInstanceEditVlansMap3k4k for the same MST instance
       both to the value of zero length can not be allowed."
    ::= {stpxSMSTInstanceEditEntry 4 }

stpxSMSTPortTable OBJECT-TYPE
    SYNTAX      SEQUENCE OF StpxSMSTPortEntry
    MAX-ACCESS  not-accessible
    STATUS      current 
    DESCRIPTION
       "A table containing port information for the MST 
       Protocol on all the bridge ports existing on the 
       system.

       This table is only instantiated when the object 
       value of stpxSpanningTreeType is mst(4)"
    ::= { stpxSMSTObjects 7 }

stpxSMSTPortEntry OBJECT-TYPE
    SYNTAX      StpxSMSTPortEntry
    MAX-ACCESS  not-accessible
    STATUS      current 
    DESCRIPTION
       "An entry with port information for the MST protocol
       on a bridge port."
    INDEX { stpxSMSTPortIndex }
    ::= { stpxSMSTPortTable 1 }

StpxSMSTPortEntry ::= SEQUENCE {
    stpxSMSTPortIndex Integer32,
    stpxSMSTPortStatus BITS,
    stpxSMSTPortAdminHelloTime Unsigned32,
    stpxSMSTPortConfigedHelloTime Unsigned32,
    stpxSMSTPortOperHelloTime Integer32
}

stpxSMSTPortIndex OBJECT-TYPE
    SYNTAX      Integer32 (1..65535)
    MAX-ACCESS  not-accessible
    STATUS      current 
    DESCRIPTION
       "The value of dot1dBasePort (i.e. dot1dBridge.1.4)
        for the bridge port."
    REFERENCE
       "dot1dBasePort is defined in RFC1493."
    ::= { stpxSMSTPortEntry 1 }

stpxSMSTPortStatus OBJECT-TYPE
    SYNTAX     BITS {
                     edge(0),
                     boundary(1),
                     pvst(2),
                     stp(3) 
               }
    MAX-ACCESS read-only
    STATUS     current 
    DESCRIPTION
       "Indicates the operational status of the port for the 
       MST protocol. 

       edge -- this port is an edge port for the MST region.

       boundary -- this port is a boundary port for the 
               MST region.

       pvst --  this port is connected to a PVST/PVST+ bridge.   
 
       stp -- this port is connected to a Single Spanning
               Tree bridge." 
   ::= { stpxSMSTPortEntry 2 }

stpxSMSTPortAdminHelloTime OBJECT-TYPE
    SYNTAX      Unsigned32 
    UNITS       "hundredth of seconds"
    MAX-ACCESS  read-write
    STATUS      current 
    DESCRIPTION
        "The adminitratively configured hello time in hundredth 
        of seconds on a port for IEEE MST. The granularity 
        of this timer is 1 second. An agent may return a badValue 
        error if a set is attempted to a value which is not a 
        whole number of seconds. This object value of zero
        means the hello time is not specifically configured on 
        this port and object value of stpxSMSTPortConfigedHelloTime
        retrieved for this port will take on the value of 
        dot1dStpBridgeHelloTime defined in BRIDGE-MIB."  
    ::= { stpxSMSTPortEntry 3 }

stpxSMSTPortConfigedHelloTime OBJECT-TYPE
    SYNTAX      Unsigned32 
    UNITS       "hundredth of seconds"
    MAX-ACCESS  read-only
    STATUS      current
    DESCRIPTION
        "Indicates the effective configuration of the hello time on 
        a port."   
    ::= { stpxSMSTPortEntry 4 }

stpxSMSTPortOperHelloTime OBJECT-TYPE
    SYNTAX      Integer32 (-1..2147483647) 
    UNITS       "hundredth of seconds"
    MAX-ACCESS  read-only
    STATUS  current
    DESCRIPTION
        "The operational hello time in hundredth of seconds on a 
        port for IEEE MST. If this object value is not
        applicable on a port, then the value retrieved on that
        port will be -1."  
    ::= { stpxSMSTPortEntry 5 } 

--
-- Notifications
--
 
stpxNotificationsPrefix OBJECT IDENTIFIER ::= { stpxNotifications 0 }
 
stpxInconsistencyUpdate NOTIFICATION-TYPE
    OBJECTS     { stpxInconsistentState }
    STATUS      current
    DESCRIPTION
             "A stpxPortInconsistencyUpdate notification is sent by a
              bridge when an instance of stpxInconsistentState is 
              created or destroyed.  That is, when an inconsistency is
              discovered in the VLAN's Spanning Tree for a particular 
              port, or when such an inconsistency disappears.  Note 
              that the trap is not sent if the port transitions between
              different types of inconsistency.
 
              The stpxInconsistentState value indicates the type of
              inconsistency which now exists/no longer exists for the 
              relevant VLAN on the relevant port."
    ::= { stpxNotificationsPrefix 1}
 
stpxRootInconsistencyUpdate NOTIFICATION-TYPE
    OBJECTS     { stpxRootInconsistencyState, stpxSpanningTreeType }
    STATUS      current
    DESCRIPTION
             "A stpxRootInconsistencyUpdate notification is sent by a
              bridge when an instance of stpxRootInconsistencyState
              is created or destroyed. That is, when an
              root-inconsistency is discovered in the VLAN's or 
              instance's Spanning Tree for a particular port, or when 
              such an root-inconsistency disappears. For creation, the 
              value of stpxRootInconsistencyState in the notification is
              true(1); for deletion, the value is false(2).
    
              The object value of stpxSpanningTreeType indicates
              which Spanning Tree protocol is running when an instance 
              of stpxRootInconsistencyState is created or destroyed.  "
    ::= { stpxNotificationsPrefix 2}

stpxLoopInconsistencyUpdate NOTIFICATION-TYPE
    OBJECTS     { stpxLoopInconsistencyState, stpxSpanningTreeType }
    STATUS      current
    DESCRIPTION
             "A stpxLoopInconsistencyUpdate notification is sent by a
              bridge when an instance of stpxLoopInconsistencyState
              is created or destroyed. That is, when an
              loop-inconsistency is discovered in the VLAN's or 
              instance's Spanning Tree for a particular port, or when 
              such an loop-inconsistency disappears. For creation, 
              the value of stpxLoopInconsistencyState in the 
              notification is true(1); for deletion, the value is 
              false(2).

              The object value of stpxSpanningTreeType indicates
              which Spanning Tree protocol is running when an instance
              of stpxLoopInconsistencyState is created or 
              destroyed."
    ::= { stpxNotificationsPrefix 3}



-- conformance information

stpxMIBConformance
                   OBJECT IDENTIFIER ::= { ciscoStpExtensionsMIB 3 }
stpxMIBCompliances 
                   OBJECT IDENTIFIER ::= { stpxMIBConformance 1 }
stpxMIBGroups
                   OBJECT IDENTIFIER ::= { stpxMIBConformance 2 }


-- compliance statements

stpxMIBCompliance MODULE-COMPLIANCE
    STATUS  deprecated 
    DESCRIPTION
            "The compliance statement for entities which implement
            Cisco STP Extensions MIB."
    MODULE  -- this module
            -- no MANDATORY-GROUPS

        GROUP        stpxUplinkGroup 
        DESCRIPTION  "This group is mandatory for implementations
                     of the UplinkFast capability."

        GROUP        stpxPreferredVlansGroup
        DESCRIPTION  "This group is mandatory for implementations
                     of the Preferred VLANs capability."
       
        GROUP        stpxNotificationsGroup
        DESCRIPTION   "The notifications which a STP extension 
                      implementation required to implement."

    ::= { stpxMIBCompliances 1 }

stpxMIBCompliance2 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."
 

    ::= { stpxMIBCompliances 2 }

stpxMIBCompliance3 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities 
                      that support MISTP and PVSTP+"

        GROUP        stpxMISTPGroup
        DESCRIPTION  "This group must be implemented by the entities 
                      that support MISTP."

    ::= { stpxMIBCompliances 3 }

stpxMIBCompliance4 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities 
                     that support MISTP and PVSTP+"

        GROUP        stpxMISTPGroup
        DESCRIPTION  "This group must be implemented by the entities 
                     that support MISTP."

        GROUP        stpxLongPathCostModeGroup
        DESCRIPTION  "This group must be implemented by the entities
                      that support 32 bits spannning tree path cost
                      value."
    ::= { stpxMIBCompliances 4 }

stpxMIBCompliance5 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopGuardGroup
        DESCRIPTION  "This group is mandatory for implementations
                     of the LoopGuard capability."

        GROUP        stpxLoopInconsistencyNotificationsGroup
        DESCRIPTION  "The notifications which a STP extension
                     implementation is required to implement."
    
        GROUP        stpxFastStartGroup
        DESCRIPTION  "This stpxFastStartGroup is an optional group
                     containing objects providing information about
                     Spanning Tree Port Fast Start feature."

    ::= { stpxMIBCompliances 5 }


stpxMIBCompliance6 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxSstpGroup
        DESCRIPTION  "This group is optional for implementations of
                     Cisco's Shared Spanning Tree Protocol (SSTP)."
 
        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopInconsistencyNotificationsGroup
        DESCRIPTION  "The notifications which a STP extension
                     implementation is required to implement."
   
        GROUP        stpxBpduSkewingGroup 
        DESCRIPTION  "This is an optional group for implementations of
                     Spanning Tree BPDU Skewing feature."
  
        GROUP        stpxFastStartGroup2
        DESCRIPTION  "This stpxFastStartGroup is an optional group
                     containing objects providing information about
                     Spanning Tree Port Fast Start feature."

        GROUP        stpxLoopGuardGroup2
        DESCRIPTION  "This group is optional for implementations
                     of the LoopGuard capability."
 
        GROUP        stpxMSTGroup
        DESCRIPTION  "This group is optional for implementation of 
                     Multiple Spanning Tree Protocol feature."
      
        GROUP        stpxPreferredMSTInstancesGroup 
        DESCRIPTION  "This group is optional for implementations
                     of Preferred MST Instance Map feature."

    ::= { stpxMIBCompliances 6 }


stpxMIBCompliance7 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxSstpGroup
        DESCRIPTION  "This group is optional for implementations of
                     Cisco's Shared Spanning Tree Protocol (SSTP)."
 
        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopInconsistencyNotificationsGroup
        DESCRIPTION  "The notifications which a STP extension
                     implementation is required to implement."
   
        GROUP        stpxBpduSkewingGroup 
        DESCRIPTION  "This is an optional group for implementations of
                     Spanning Tree BPDU Skewing feature."
  
        GROUP        stpxFastStartGroup2
        DESCRIPTION  "This stpxFastStartGroup is an optional group
                     containing objects providing information about
                     Spanning Tree Port Fast Start feature."

        GROUP        stpxLoopGuardGroup2
        DESCRIPTION  "This group is optional for implementations
                     of the LoopGuard capability."
 
        GROUP        stpxPreferredMSTInstancesGroup 
        DESCRIPTION  "This group is optional for implementations
                     of Preferred MST Instance Map feature."

        GROUP        stpxFastStartGroup3 
        DESCRIPTION  "This group is optional for implementations
                     of Bpdu Guard and Bpdu Filter feature."

        GROUP        stpxUplinkGroup2
        DESCRIPTION  "This group is optional for implementations
                     of UplinkFast feature."

        GROUP        stpxBackboneGroup2
        DESCRIPTION  "This group is optional for implementations
                     of BackboneFast feature." 
 
        GROUP        stpxMSTGroup2
        DESCRIPTION  "This group is optional for implementation of
                     Multiple Spanning Tree Protocol feature."

        GROUP        stpxRSTPGroup
        DESCRIPTION  "This group is optional for implementation of
                     Rapid Spanning Tree Protocol feature." 

        GROUP        stpxRPVSTGroup
        DESCRIPTION  "This group is optional for implementation of
                     Rapid PVST+ feature." 
    ::= { stpxMIBCompliances 7 }

stpxMIBCompliance8 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxSstpGroup
        DESCRIPTION  "This group is optional for implementations of
                     Cisco's Shared Spanning Tree Protocol (SSTP)."
 
        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopInconsistencyNotificationsGroup
        DESCRIPTION  "The notifications which a STP extension
                     implementation is required to implement."
   
        GROUP        stpxBpduSkewingGroup 
        DESCRIPTION  "This is an optional group for implementations of
                     Spanning Tree BPDU Skewing feature."
  
        GROUP        stpxFastStartGroup2
        DESCRIPTION  "This stpxFastStartGroup is an optional group
                     containing objects providing information about
                     Spanning Tree Port Fast Start feature."

        GROUP        stpxLoopGuardGroup2
        DESCRIPTION  "This group is optional for implementations
                     of the LoopGuard capability."
 
        GROUP        stpxPreferredMSTInstancesGroup 
        DESCRIPTION  "This group is optional for implementations
                     of Preferred MST Instance Map feature."

        GROUP        stpxFastStartGroup3 
        DESCRIPTION  "This group is optional for implementations
                     of Bpdu Guard and Bpdu Filter feature."

        GROUP        stpxUplinkGroup2
        DESCRIPTION  "This group is optional for implementations
                     of UplinkFast feature."

        GROUP        stpxBackboneGroup2
        DESCRIPTION  "This group is optional for implementations
                     of BackboneFast feature." 
 
        GROUP        stpxMSTGroup2
        DESCRIPTION  "This group is optional for implementation of
                     Multiple Spanning Tree Protocol feature."

        GROUP        stpxRSTPGroup
        DESCRIPTION  "This group is optional for implementation of
                     Rapid Spanning Tree Protocol feature." 

        GROUP        stpxRPVSTGroup
        DESCRIPTION  "This group is optional for implementation of
                     Rapid PVST+ feature." 

        GROUP        stpxExtendedSysIDGroup
        DESCRIPTION  "This group is mandatory for implementation of
                     Extended System ID feature." 

        GROUP        stpxNotificationEnableGroup
        DESCRIPTION "This group is mandatory for implementation of
                     control on the generation of Spanning Tree
                     notifications."

        GROUP        stpxFastStartOperModeGroup
        DESCRIPTION "This group is mandatory for implementation of
                     Spanning Tree Port Fast Start Oper Mode feature." 

    ::= { stpxMIBCompliances 8 }

stpxMIBCompliance9 MODULE-COMPLIANCE
    STATUS  deprecated 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxSstpGroup
        DESCRIPTION  "This group is optional for implementations of
                     Cisco's Shared Spanning Tree Protocol (SSTP)."
 
        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopInconsistencyNotificationsGroup
        DESCRIPTION  "The notifications which a STP extension
                     implementation is required to implement."
   
        GROUP        stpxBpduSkewingGroup 
        DESCRIPTION  "This is an optional group for implementations of
                     Spanning Tree BPDU Skewing feature."
  
        GROUP        stpxFastStartGroup2
        DESCRIPTION  "This stpxFastStartGroup is an optional group
                     containing objects providing information about
                     Spanning Tree Port Fast Start feature."

        GROUP        stpxLoopGuardGroup2
        DESCRIPTION  "This group is optional for implementations
                     of the LoopGuard capability."
 
        GROUP        stpxFastStartGroup3 
        DESCRIPTION  "This group is optional for implementations
                     of Bpdu Guard and Bpdu Filter feature."

        GROUP        stpxUplinkGroup2
        DESCRIPTION  "This group is optional for implementations
                     of UplinkFast feature."

        GROUP        stpxBackboneGroup2
        DESCRIPTION  "This group is optional for implementations
                     of BackboneFast feature." 
 
        GROUP        stpxRSTPGroup
        DESCRIPTION  "This group is optional for implementation of
                     Rapid Spanning Tree Protocol feature." 

        GROUP        stpxRPVSTGroup
        DESCRIPTION  "This group is optional for implementation of
                     Rapid PVST+ feature." 

        GROUP        stpxExtendedSysIDGroup
        DESCRIPTION  "This group is mandatory for implementation of
                     Extended System ID feature." 

        GROUP        stpxNotificationEnableGroup
        DESCRIPTION "This group is mandatory for implementation of
                     control on the generation of Spanning Tree
                     notifications."

        GROUP        stpxFastStartOperModeGroup
        DESCRIPTION "This group is mandatory for implementation of
                     Spanning Tree Port Fast Start Oper Mode feature."

        GROUP        stpxMSTGroup3 
        DESCRIPTION "This group is mandatory for implementation of  
                     Multiple Spanning Tree Protocol on the device."

        GROUP       stpxSMSTGroup
        DESCRIPTION "This group is mandatory for implementation of  
                    supporting IEEE MST on the device."

        GROUP       stpxSMSTInstanceGroup 
        DESCRIPTION "This group is mandatory for implementation of 
                    supporting MST instance information for 
                    IEEE MST on the device."

        GROUP       stpxSMSTInstanceEditGroup
        DESCRIPTION "This group is mandatory for implementation of
                    supporting MST instance edit information for
                    IEEE MST on the device."

        GROUP       stpxSMSTPortStatusGroup
        DESCRIPTION "This group is mandatory for implementation of 
                    port status information for Multiple Spanning
                    Tree Protocol on the device."

        GROUP       stpxSMSTPortHelloTimeGroup
        DESCRIPTION "This group is mandatory for implementation of 
                    port hello time information for IEEE MST 
                    on the device."

    ::= { stpxMIBCompliances 9 }

stpxMIBCompliance10 MODULE-COMPLIANCE
    STATUS  current 
    DESCRIPTION
            "The compliance statement for entities which implement
            Cisco STP Extensions MIB."
    MODULE  -- this module
            -- no MANDATORY-GROUPS

        GROUP        stpxUplinkGroup
        DESCRIPTION  "This group is mandatory for implementations
                     of the UplinkFast capability."

        GROUP        stpxSstpGroup
        DESCRIPTION  "This group is optional for implementations of
                     Cisco's Shared Spanning Tree Protocol (SSTP)."
 
        GROUP        stpxPreferredVlansGroup
        DESCRIPTION  "This group is mandatory for implementations
                     of the Preferred VLANs capability."

        GROUP        stpxNotificationsGroup
        DESCRIPTION   "The notifications which a STP extension
                      implementation required to implement."

        GROUP        stpxBackboneGroup
        DESCRIPTION  "This group is mandatory for implementations
                     of the BackboneFast capability."

        GROUP        stpxRootGuardGroup
        DESCRIPTION  "This group is mandatory for implementations
                     of the RootGuard capability."

        GROUP        stpxRootInconsistencyNotificationsGroup
        DESCRIPTION  "The notifications which a STP extension
                      implementation required to implement."

        GROUP        stpx4kVlanGroup
        DESCRIPTION  "This group must be implemented by the
                     entities which support the range of VlanIndex
                     between 1024 and 4095."

        GROUP        stpxSpanningTreeGroup
        DESCRIPTION  "This group must be implemented by the entities
                     that support MISTP and PVSTP+"

        GROUP        stpxMISTPGroup
        DESCRIPTION  "This group must be implemented by the entities
                     that support MISTP."

        GROUP        stpxLongPathCostModeGroup
        DESCRIPTION  "This group must be implemented by the entities
                      that support 32 bits spannning tree path cost
                      value."

        GROUP        stpxPVSTVlanGroup
        DESCRIPTION  "This group is optional for implementations
                      of the Spanning Tree PVST+ Protocol VLAN 
                      configuration."

        GROUP        stpxMISTPGroup2
        DESCRIPTION  "This group is optional for implementations
                      that support MISTP with the range of VlanIndex
                      up to 4095."
     
        GROUP        stpxLoopInconsistencyNotificationsGroup
        DESCRIPTION  "The notifications which a STP extension
                     implementation is required to implement."
   
        GROUP        stpxBpduSkewingGroup 
        DESCRIPTION  "This is an optional group for implementations of
                     Spanning Tree BPDU Skewing feature."
  
        GROUP        stpxFastStartGroup2
        DESCRIPTION  "This stpxFastStartGroup is an optional group
                     containing objects providing information about
                     Spanning Tree Port Fast Start feature."

        GROUP        stpxLoopGuardGroup2
        DESCRIPTION  "This group is optional for implementations
                     of the LoopGuard capability."
 
        GROUP        stpxFastStartGroup3 
        DESCRIPTION  "This group is optional for implementations
                     of Bpdu Guard and Bpdu Filter feature."

        GROUP        stpxUplinkGroup2
        DESCRIPTION  "This group is optional for implementations
                     of UplinkFast feature."

        GROUP        stpxBackboneGroup2
        DESCRIPTION  "This group is optional for implementations
                     of BackboneFast feature." 
 
        GROUP        stpxRSTPGroup
        DESCRIPTION  "This group is optional for implementation of
                     Rapid Spanning Tree Protocol feature." 

        GROUP        stpxRPVSTGroup
        DESCRIPTION  "This group is optional for implementation of
                     Rapid PVST+ feature." 

        GROUP        stpxExtendedSysIDGroup
        DESCRIPTION  "This group is mandatory for implementation of
                     Extended System ID feature." 

        GROUP        stpxNotificationEnableGroup
        DESCRIPTION "This group is mandatory for implementation of
                     control on the generation of Spanning Tree
                     notifications."

        GROUP        stpxFastStartOperModeGroup
        DESCRIPTION "This group is mandatory for implementation of
                     Spanning Tree Port Fast Start Oper Mode feature."

        GROUP        stpxMSTGroup3 
        DESCRIPTION "This group is mandatory for implementation of  
                     Multiple Spanning Tree Protocol on the device."

        GROUP       stpxSMSTGroup
        DESCRIPTION "This group is mandatory for implementation of  
                    supporting IEEE MST on the device."

        GROUP       stpxSMSTInstanceGroup 
        DESCRIPTION "This group is mandatory for implementation of 
                    supporting MST instance information for 
                    IEEE MST on the device."

        GROUP       stpxSMSTInstanceEditGroup
        DESCRIPTION "This group is mandatory for implementation of
                    supporting MST instance edit information for
                    IEEE MST on the device."

        GROUP       stpxSMSTPortStatusGroup
        DESCRIPTION "This group is mandatory for implementation of 
                    port status information for Multiple Spanning
                    Tree Protocol on the device."

        GROUP       stpxSMSTPortHelloTimeGroup
        DESCRIPTION "This group is mandatory for implementation of 
                    port hello time information for IEEE MST 
                    on the device."

        GROUP       stpxSMSTInstanceCISTGroup
        DESCRIPTION "This group is mandatory for implementation of
                    supporting Common and Internal Spanning Tree (CIST)
                    information for IEEE MST on the device."

    ::= { stpxMIBCompliances 10 }

-- units of conformance

stpxUplinkGroup OBJECT-GROUP
    OBJECTS { stpxUplinkFastEnabled,
              stpxUplinkFastTransitions,
              stpxUplinkStationLearningGenRate,
              stpxUplinkStationLearningFrames }
    STATUS  current
    DESCRIPTION
            "A collection of objects for managing the UplinkFast
            capability."
    ::= { stpxMIBGroups 1 }

stpxPreferredVlansGroup OBJECT-GROUP
    OBJECTS { stpxPreferredVlansMap }
    STATUS  current
    DESCRIPTION
            "A collection of objects for indicating preferred VLANs."
    ::= { stpxMIBGroups 2 }

stpxSstpGroup OBJECT-GROUP
    OBJECTS { stpxInconsistentState }
    STATUS  current
    DESCRIPTION
            "A collection of objects to support Cisco's Shared Spanning
            Tree Protocol (SSTP)."
    ::= { stpxMIBGroups 3 }

stpxNotificationsGroup NOTIFICATION-GROUP
    NOTIFICATIONS { stpxInconsistencyUpdate }
    STATUS        current
    DESCRIPTION
            "The notifications which a STP extension implementation is
             required to implement."
    ::= { stpxMIBGroups 4 }

stpxBackboneGroup OBJECT-GROUP
    OBJECTS { stpxBackboneFastEnabled,
              stpxBackboneFastInInferiorBPDUs,
              stpxBackboneFastInRLQRequestPDUs,
              stpxBackboneFastInRLQResponsePDUs,
              stpxBackboneFastOutRLQRequestPDUs,
              stpxBackboneFastOutRLQResponsePDUs }
    STATUS  current
    DESCRIPTION
            "A collection of objects for managing the BackboneFast
            capability."
    ::= { stpxMIBGroups 5 }

stpxRootGuardGroup OBJECT-GROUP
    OBJECTS { stpxRootGuardConfigEnabled,
              stpxRootInconsistencyState
            }
    STATUS  current
    DESCRIPTION
            "A collection of objects to support root guard
            capabilities."
    ::= { stpxMIBGroups 6 }

stpxRootInconsistencyNotificationsGroup NOTIFICATION-GROUP
    NOTIFICATIONS { stpxRootInconsistencyUpdate }
    STATUS        current
    DESCRIPTION
            "The notifications which a STP root guard 
              implementation is required to implement."
    ::= { stpxMIBGroups 7 }

stpx4kVlanGroup OBJECT-GROUP
    OBJECTS { stpxPreferredVlansMap2k,
              stpxPreferredVlansMap3k,
              stpxPreferredVlansMap4k }
    STATUS  current
    DESCRIPTION
            "A collection of objects providing information
            for VLANS with VlanIndex from 1024 to 4095."
    ::= { stpxMIBGroups 8 }

stpxSpanningTreeGroup OBJECT-GROUP
    OBJECTS { stpxSpanningTreeType }
    STATUS  current
    DESCRIPTION
            "An object selecting what kind of spanning tree protocol."
    ::= { stpxMIBGroups 9 }

stpxMISTPGroup  OBJECT-GROUP
    OBJECTS {   stpxMISTPInstanceNumber,
                stpxMISTPInstanceEnable, 
                stpxVlanMISTPInstMapInstIndex,
                stpxVlanMISTPInstMapEditInstIndex,
                stpxPreferredMISTPInstancesMap }
    STATUS  current
    DESCRIPTION
            "A collection objects managing the information of
             MISTP feature."
    ::= { stpxMIBGroups 10 }   

stpxLongPathCostModeGroup OBJECT-GROUP
    OBJECTS {   stpxSpanningTreePathCostMode,
                stpxLongStpPortPathCost }
    STATUS  current
    DESCRIPTION
            "A collection objects managing the information of
            spanning tree path cost in 32 bits value."
    ::= { stpxMIBGroups 11 }

stpxPVSTVlanGroup OBJECT-GROUP
     OBJECTS {  stpxPVSTVlanEnable }
     STATUS  current
     DESCRIPTION
             "A collection of objects managing the information 
             of Spanning Tree PVST+ protocol VLAN configuration." 
     ::= { stpxMIBGroups 12 }

stpxMISTPGroup2 OBJECT-GROUP
     OBJECTS {  stpxMISTPInstanceVlansMapped,
                stpxMISTPInstanceVlansMapped2k,
                stpxMISTPInstanceVlansMapped3k,
                stpxMISTPInstanceVlansMapped4k }
     STATUS  current
     DESCRIPTION
             "A collection objects managing the information of
             MISTP instances to VLAN mapping with the range of
             VlanIndex up to 4095." 
     ::= { stpxMIBGroups 13 }

stpxLoopGuardGroup OBJECT-GROUP
    OBJECTS { stpxLoopGuardConfigEnabled,
              stpxLoopInconsistencyState
            }
    STATUS  deprecated 
    DESCRIPTION
            "A collection of objects to support LoopGuard 
            capabilities."
    ::= { stpxMIBGroups 14 }

stpxLoopInconsistencyNotificationsGroup NOTIFICATION-GROUP
    NOTIFICATIONS { stpxLoopInconsistencyUpdate }
    STATUS        current
    DESCRIPTION
            "The notifications which a STP LoopGuard 
              implementation is required to implement."
    ::= { stpxMIBGroups 15 }

stpxFastStartGroup OBJECT-GROUP
    OBJECTS { stpxFastStartBpduGuardEnable,
              stpxFastStartBpduFilterEnable,
              stpxFastStartPortEnable }
    STATUS  deprecated 
    DESCRIPTION
            "A collection of objects to support Spanning Tree Port
            Fast Start feature."
    ::= { stpxMIBGroups 16 }

stpxBpduSkewingGroup OBJECT-GROUP
    OBJECTS { stpxBpduSkewingDetectionEnable,
              stpxBpduSkewingLastSkewDuration,
              stpxBpduSkewingWorstSkewDuration,
              stpxBpduSkewingWorstSkewTime }
    STATUS  current
    DESCRIPTION
            "This is an optional group with a collection of
            objects to support Spanning Tree BPDU Skewing feature."
    ::= { stpxMIBGroups 17 }

stpxFastStartGroup2 OBJECT-GROUP
    OBJECTS { stpxFastStartBpduGuardEnable,
              stpxFastStartBpduFilterEnable, 
              stpxFastStartPortMode,
              stpxFastStartGlobalDefaultMode 
            }
    STATUS  current
    DESCRIPTION
            "An optional group with a collection of objects to 
            support Fast Start global default mode on the device."
    ::= { stpxMIBGroups 18 }

stpxLoopGuardGroup2 OBJECT-GROUP
    OBJECTS { stpxLoopInconsistencyState, 
              stpxLoopGuardConfigMode,
              stpxLoopGuardGlobalDefaultMode 
            }
    STATUS  current
    DESCRIPTION
            "An optional group with a collection of objects to 
            support Loop Guard global default mode on the device."
    ::= { stpxMIBGroups 19 }

stpxMSTGroup OBJECT-GROUP
    OBJECTS { stpxMSTMaxInstanceNumber,
              stpxMSTRegionName,
              stpxMSTRegionRevision,
              stpxMSTInstanceVlansMapped,
              stpxMSTInstanceVlansMapped2k,
              stpxMSTInstanceVlansMapped3k,
              stpxMSTInstanceVlansMapped4k,
              stpxMSTInstanceRemainingHopCount,
              stpxMSTRegionEditBufferStatus,
              stpxMSTRegionEditBufferOperation,
              stpxMSTRegionEditName,
              stpxMSTRegionEditRevision,
              stpxMSTInstanceEditVlansMap,
              stpxMSTInstanceEditVlansMap2k,
              stpxMSTInstanceEditVlansMap3k,
              stpxMSTInstanceEditVlansMap4k,
              stpxMSTPortAdminLinkType,  -- deprecated
              stpxMSTPortOperLinkType,   -- deprecated
              stpxMSTPortProtocolMigration,  -- deprecated
              stpxMSTPortStatus,  
              stpxMSTPortRoleValue,  -- deprecated
              stpxMSTMaxHopCount
                }
    STATUS  deprecated 
    DESCRIPTION
            "An optional group with a collection of objects to 
            support Multiple Spanning Tree Protocol on the device."
    ::= { stpxMIBGroups 20 }

stpxPreferredMSTInstancesGroup OBJECT-GROUP
    OBJECTS { stpxPreferredMSTInstancesMap } 
    STATUS  deprecated
    DESCRIPTION
            "An optional group with a collection of objects to
            support Preferred MST Instance Map feature for Multiple 
            Spanning Tree Protocol on the device."
        ::= { stpxMIBGroups 21 }

stpxFastStartGroup3 OBJECT-GROUP
    OBJECTS { stpxFastStartPortBpduGuardMode,
              stpxFastStartPortBpduFilterMode
            }
    STATUS  current
    DESCRIPTION
            "An optional group with a collection of objects to
            support per port Bpdu Guard and Bpdu Filter mode 
            configuration on the device."
    ::= { stpxMIBGroups 22 }

stpxUplinkGroup2 OBJECT-GROUP
    OBJECTS { stpxUplinkFastOperEnabled }
    STATUS  current
    DESCRIPTION
            "An optional group with a collection of objects to
            manage the UplinkFast capability."
    ::= { stpxMIBGroups 23 }

stpxBackboneGroup2 OBJECT-GROUP
    OBJECTS { stpxBackboneFastOperEnabled }
    STATUS  current
    DESCRIPTION
            "An optional group with a collection of objects to 
            manage the BackboneFast capability."
    ::= { stpxMIBGroups 24 }


stpxMSTGroup2 OBJECT-GROUP
    OBJECTS { stpxMSTMaxInstanceNumber, -- deprecated
              stpxMSTRegionName,
              stpxMSTRegionRevision, -- deprecated
              stpxMSTInstanceVlansMapped, -- deprecated
              stpxMSTInstanceVlansMapped2k, -- deprecated
              stpxMSTInstanceVlansMapped3k, -- deprecated
              stpxMSTInstanceVlansMapped4k, -- deprecated
              stpxMSTInstanceRemainingHopCount, -- deprecated
              stpxMSTRegionEditBufferStatus,
              stpxMSTRegionEditBufferOperation,
              stpxMSTRegionEditName,
              stpxMSTRegionEditRevision, -- deprecated
              stpxMSTInstanceEditVlansMap, -- deprecated
              stpxMSTInstanceEditVlansMap2k, -- deprecated
              stpxMSTInstanceEditVlansMap3k, -- deprecated
              stpxMSTInstanceEditVlansMap4k, -- deprecated
              stpxMSTPortStatus, -- deprecated
              stpxMSTMaxHopCount
            }
    STATUS  deprecated 
    DESCRIPTION
            "An optional group with a collection of objects to 
            support Multiple Spanning Tree Protocol on the device."
    ::= { stpxMIBGroups 25 }

stpxRSTPGroup OBJECT-GROUP
    OBJECTS { stpxRSTPPortAdminLinkType,
              stpxRSTPPortOperLinkType,
              stpxRSTPPortProtocolMigration,
              stpxRSTPPortRoleValue  
            }
    STATUS  current
    DESCRIPTION
            "An optional group with a collection of objects to
            support Rapid Spanning Tree Protocol on the device."
    ::= { stpxMIBGroups 26 }

stpxRPVSTGroup OBJECT-GROUP
    OBJECTS { 
             stpxRPVSTPortStatus
            }
    STATUS  current
    DESCRIPTION
            "An optional group with a collection of objects to
            support Rapid PVST+ on the device."
    ::= { stpxMIBGroups 27 }

stpxExtendedSysIDGroup OBJECT-GROUP
    OBJECTS { 
             stpxExtendedSysIDAdminEnabled,
             stpxExtendedSysIDOperEnabled
            }
    STATUS  current
    DESCRIPTION
            "A collection of objects to manage the 
            Extended System ID capability."
   ::= { stpxMIBGroups 28 }

stpxNotificationEnableGroup OBJECT-GROUP
    OBJECTS { stpxNotificationEnable }
    STATUS  current
    DESCRIPTION
            "A collection of objects providing control on the 
            generation of Spanning Tree notifications." 
    ::= { stpxMIBGroups 29 }

stpxFastStartOperModeGroup OBJECT-GROUP
    OBJECTS { stpxFastStartOperMode }
    STATUS  current
    DESCRIPTION
            "A collection of objects providing Spanning Tree 
            Port Fast Start Operatioanl information on a port." 
    ::= { stpxMIBGroups 30 }

stpxMSTGroup3 OBJECT-GROUP
    OBJECTS {
              stpxMSTRegionName,
              stpxMSTRegionEditBufferStatus,
              stpxMSTRegionEditBufferOperation,
              stpxMSTRegionEditName,
              stpxMSTMaxHopCount
            }
    STATUS  current
    DESCRIPTION
            "A collection of objects providing support 
            for Multiple Spanning Tree Protocol on the device."
    ::= { stpxMIBGroups 31 }

stpxSMSTGroup OBJECT-GROUP
    OBJECTS {
              stpxSMSTMaxInstances,
              stpxSMSTMaxInstanceID,
              stpxSMSTRegionRevision,
              stpxSMSTRegionEditRevision
            }
    STATUS  current
    DESCRIPTION
            "A collection of objects providing support for
            IEEE MST on the device."
    ::= { stpxMIBGroups 32 }

stpxSMSTInstanceGroup OBJECT-GROUP
    OBJECTS {
              stpxSMSTInstanceVlansMapped1k2k,
              stpxSMSTInstanceVlansMapped3k4k,
              stpxSMSTInstanceRemainingHopCount
            }
    STATUS  current
    DESCRIPTION
            "A collection of objects providing support for 
            MST instance information for IEEE MST on the device."
    ::= { stpxMIBGroups 33 }

stpxSMSTInstanceEditGroup OBJECT-GROUP
    OBJECTS {
              stpxSMSTInstanceEditVlansMap1k2k,
              stpxSMSTInstanceEditVlansMap3k4k,
              stpxSMSTInstanceEditRowStatus
            }
    STATUS  current
    DESCRIPTION
            "A collection of objects providing support for MST 
            instance edit information for IEEE MST on the device."
    ::= { stpxMIBGroups 34 }

stpxSMSTPortStatusGroup OBJECT-GROUP
    OBJECTS {
              stpxSMSTPortStatus
            }
    STATUS  current
    DESCRIPTION
            "A collection of objects providing support for  
            port status information for MST Protocol on the
            device."
    ::= { stpxMIBGroups 35 }

stpxSMSTPortHelloTimeGroup OBJECT-GROUP
    OBJECTS {
              stpxSMSTPortAdminHelloTime,
              stpxSMSTPortConfigedHelloTime,
              stpxSMSTPortOperHelloTime
            }
    STATUS  current
    DESCRIPTION
            "A collection of objects providing support for per 
            port hello time information for IEEE MST on the device."
    ::= { stpxMIBGroups 36 }

stpxSMSTInstanceCISTGroup OBJECT-GROUP
    OBJECTS { 
              stpxSMSTInstanceCISTRegionalRoot,
              stpxSMSTInstanceCISTIntRootCost
            }
    STATUS  current
    DESCRIPTION
            "A collection of objects providing information about 
            Common and Internal Spanning Tree (CIST) for IEEE 
            MST on the device."
    ::= { stpxMIBGroups 37 }  

END
