--
-- This SMIv1 module has been generated by smidump 0.2-cvs. Do not edit.
--

GNOME-SMI DEFINITIONS ::= BEGIN

IMPORTS
    enterprises
        FROM SNMPv2-SMI;

gnome OBJECT IDENTIFIER
    ::= { enterprises 3317 }

-- gnome MODULE-IDENTITY
--     LAST-UPDATED    "199809010000Z"
--     ORGANIZATION    
--             "GNOME project"
--     CONTACT-INFO    
--             "GNU Network Object Model Environment project
--              
--              see http://www.gnome.org for contact persons of a particular
--              area or subproject of GNOME.
--              
--              Administrative contact for MIB module:
--              
--              Jochen Friedrich
--              Wingertstr. 70/1
--              68809 Neulussheim
--              Germany 
--              
--              email: snmp@gnome.org"
--     DESCRIPTION     
--             "The Structure of GNOME."
--     ::= { enterprises 3317 }


gnomeProducts OBJECT IDENTIFIER
    ::= { gnome 1 }

gnomeMgmt OBJECT IDENTIFIER
    ::= { gnome 2 }

gnomeTest OBJECT IDENTIFIER
    ::= { gnome 3 }

END -- end of module GNOME-SMI.
