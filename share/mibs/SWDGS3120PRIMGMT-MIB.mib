-- *****************************************************************************
-- proprietary management MIB
-- *****************************************************************************



SWDGS3120PRIMGMT-MIB    DEFINITIONS ::= BEGIN

    IMPORTS
        MODULE-IDENTITY             FROM SNMPv2-SMI
        dlink-mgmt,dlink-products   FROM DLINK-ID-REC-MIB;

    
    
    -- 
--   DGS3120 series Product 
-- 

    dlink-Dgs3120Prod			OBJECT IDENTIFIER ::= { dlink-products 117 }
    dlink-Dgs3120ProdModel			OBJECT IDENTIFIER ::= { dlink-Dgs3120Prod 1 }
    dlink-Dgs3120Prod-Dgs3120-24TC			OBJECT IDENTIFIER ::= { dlink-Dgs3120ProdModel 1 }
    dlink-Dgs3120Prod-Dgs3120-24PC			OBJECT IDENTIFIER ::= { dlink-Dgs3120ProdModel 2 }
    dlink-Dgs3120Prod-Dgs3120-24SC			OBJECT IDENTIFIER ::= { dlink-Dgs3120ProdModel 3 }
    dlink-Dgs3120Prod-Dgs3120-48TC			OBJECT IDENTIFIER ::= { dlink-Dgs3120ProdModel 4 }
    dlink-Dgs3120Prod-Dgs3120-48PC			OBJECT IDENTIFIER ::= { dlink-Dgs3120ProdModel 5 }
    dlink-Dgs3120Prod-Dgs3120-24SC-DC		OBJECT IDENTIFIER ::= { dlink-Dgs3120ProdModel 6 }


    dlink-Dgs3120Proj			OBJECT IDENTIFIER ::= { dlink-mgmt 117 }
    dlink-Dgs3120ProjModel			OBJECT IDENTIFIER ::= { dlink-Dgs3120Proj 1 }
    dlink-Dgs3120Proj-Dgs3120-24TC			OBJECT IDENTIFIER ::= { dlink-Dgs3120ProjModel 1 }
    dlink-Dgs3120Proj-Dgs3120-24PC			OBJECT IDENTIFIER ::= { dlink-Dgs3120ProjModel 2 }
    dlink-Dgs3120Proj-Dgs3120-24SC			OBJECT IDENTIFIER ::= { dlink-Dgs3120ProjModel 3 }
    dlink-Dgs3120Proj-Dgs3120-48TC			OBJECT IDENTIFIER ::= { dlink-Dgs3120ProjModel 4 }
    dlink-Dgs3120Proj-Dgs3120-48PC			OBJECT IDENTIFIER ::= { dlink-Dgs3120ProjModel 5 }
    dlink-Dgs3120Proj-Dgs3120-24SC-DC		OBJECT IDENTIFIER ::= { dlink-Dgs3120ProjModel 6 }    
   

END
