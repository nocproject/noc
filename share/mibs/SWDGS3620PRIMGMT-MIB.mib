-- *****************************************************************************
-- proprietary management MIB
-- *****************************************************************************



SWDGS3620PRIMGMT-MIB    DEFINITIONS ::= BEGIN

    IMPORTS
        MODULE-IDENTITY             FROM SNMPv2-SMI
        dlink-mgmt,dlink-products   FROM DLINK-ID-REC-MIB;

    
    
    -- 
--   DGS3620 series Product 
-- 

    dlink-Dgs3620Prod			OBJECT IDENTIFIER ::= { dlink-products 118 }
    dlink-Dgs3620Prod-Dgs3620-28TC			OBJECT IDENTIFIER ::= { dlink-Dgs3620Prod 1 }
    dlink-Dgs3620Prod-Dgs3620-28SC			OBJECT IDENTIFIER ::= { dlink-Dgs3620Prod 2 }
    dlink-Dgs3620Prod-Dgs3620-28PC			OBJECT IDENTIFIER ::= { dlink-Dgs3620Prod 3 }
    dlink-Dgs3620Prod-Dgs3620-52T			OBJECT IDENTIFIER ::= { dlink-Dgs3620Prod 4 }
    dlink-Dgs3620Prod-Dgs3620-52P			OBJECT IDENTIFIER ::= { dlink-Dgs3620Prod 5 }
    dlink-Dgs3620Prod-Dgs3620-28TC-DC			OBJECT IDENTIFIER ::= { dlink-Dgs3620Prod 8 }
    dlink-Dgs3620Prod-Dgs3620-28SC-DC			OBJECT IDENTIFIER ::= { dlink-Dgs3620Prod 9 }


    dlink-Dgs3620Proj			OBJECT IDENTIFIER ::= { dlink-mgmt 118 }
    dlink-Dgs3620Proj-Dgs3620-28TC			OBJECT IDENTIFIER ::= { dlink-Dgs3620Proj 1 }
    dlink-Dgs3620Proj-Dgs3620-28SC			OBJECT IDENTIFIER ::= { dlink-Dgs3620Proj 2 }
    dlink-Dgs3620Proj-Dgs3620-28PC			OBJECT IDENTIFIER ::= { dlink-Dgs3620Proj 3 }
    dlink-Dgs3620Proj-Dgs3620-52T			OBJECT IDENTIFIER ::= { dlink-Dgs3620Proj 4 }
    dlink-Dgs3620Proj-Dgs3620-52P			OBJECT IDENTIFIER ::= { dlink-Dgs3620Proj 5 }
    dlink-Dgs3620Proj-Dgs3620-28TC-DC			OBJECT IDENTIFIER ::= { dlink-Dgs3620Proj 8 }
    dlink-Dgs3620Proj-Dgs3620-28SC-DC			OBJECT IDENTIFIER ::= { dlink-Dgs3620Proj 9 }
    
   

END
