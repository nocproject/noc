SWPRIMGMT-MIB    DEFINITIONS ::= BEGIN

    IMPORTS
        MODULE-IDENTITY             FROM SNMPv2-SMI
        dlink-mgmt                  FROM DLINK-ID-REC-MIB;

    des30xxSeriesProd   OBJECT IDENTIFIER ::= { dlink-mgmt 63 }
    des3010             OBJECT IDENTIFIER ::= { des30xxSeriesProd 1 }
    des3010f            OBJECT IDENTIFIER ::= { des3010 1 }
    des3010g            OBJECT IDENTIFIER ::= { des3010 2 }
    des3018             OBJECT IDENTIFIER ::= { des30xxSeriesProd 2 }
    des3026             OBJECT IDENTIFIER ::= { des30xxSeriesProd 3 }
    des3010fl           OBJECT IDENTIFIER ::= { des30xxSeriesProd 4 }
    des3016             OBJECT IDENTIFIER ::= { des30xxSeriesProd 10 }

    des3226sSeriesProd  OBJECT IDENTIFIER ::= { dlink-mgmt 48 }
    des3226stkProd      OBJECT IDENTIFIER ::= { des3226sSeriesProd 1 }
    des3226s            OBJECT IDENTIFIER ::= { des3226stkProd 1 }

    des3326sSeriesProd  OBJECT IDENTIFIER ::= { dlink-mgmt 49 }
    des3326stkProd      OBJECT IDENTIFIER ::= { des3326sSeriesProd 1 }
    des3326srProd       OBJECT IDENTIFIER ::= { des3326sSeriesProd 2 }
    des3326s            OBJECT IDENTIFIER ::= { des3326stkProd 1 }
    des3326sr           OBJECT IDENTIFIER ::= { des3326srProd 1 }

END
