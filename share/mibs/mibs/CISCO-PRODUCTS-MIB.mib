-- *****************************************************************
-- CISCO-PRODUCTS-MIB.my:  Cisco Product Object Identifier Assignments
--   
-- January 1995, Jeffrey T. Johnson
--   
-- Copyright (c) 1995-2010 by cisco Systems, Inc.
-- All rights reserved.
--   
-- *****************************************************************
--   

CISCO-PRODUCTS-MIB DEFINITIONS ::= BEGIN

IMPORTS
    MODULE-IDENTITY
        FROM SNMPv2-SMI
    ciscoModules,
    ciscoProducts
        FROM CISCO-SMI;

ciscoProductsMIB MODULE-IDENTITY
    LAST-UPDATED    "201012020000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "This module defines the object identifiers that are
        assigned to various hardware platforms, and hence are
        returned as values for sysObjectID"
    REVISION        "201012020000Z"
    DESCRIPTION
        "Removed DNP for 2960s, 3560x and 3750x"
    REVISION        "201009030000Z"
    DESCRIPTION
        "Added new product oids"
    REVISION        "200505051930Z"
    DESCRIPTION
        "Added following OIDs:
        ciscoMPX, ciscoNMCUEEC, ciscoWLSE1132, 
        ciscoME6340ACA, ciscoME6340DCA,
        ciscoME6340DCA, catalyst296024TT,
        catalyst296048TT"
    REVISION        "200504201930Z"
    DESCRIPTION
        "Removed DNP of catalyst6kGateway"
    REVISION        "200504181930Z"
    DESCRIPTION
        "Added following OIDs:
        ciscoNme16Es1GeNoPwr, ciscoNmeX24Es1GeNoPwr,
        ciscoNmeXd24Es2StNoPwr, ciscoNmeXd48Es2GeNoPwr,
        catalyst6kMsfc2a, ciscoEDI, ciscoCe611K9,
        ciscoWLSEs20."
    REVISION        "200204051400Z"
    DESCRIPTION
        "CANA Assignments."
    REVISION        "9505310000Z"
    DESCRIPTION
        "Miscellaneous updates."
    ::= { ciscoModules 2 }
-- older cisco routers (i.e. CGS, MGS, AGS) do not have the ability
-- to determine what kind of router they are.  these devices return
-- a sysObjectID value that indicates their configured functionality

ciscoGatewayServer  OBJECT IDENTIFIER
    ::= { ciscoProducts 1 }

ciscoTerminalServer  OBJECT IDENTIFIER
    ::= { ciscoProducts 2 }

ciscoTrouter  OBJECT IDENTIFIER
    ::= { ciscoProducts 3 }

ciscoProtocolTranslator  OBJECT IDENTIFIER
    ::= { ciscoProducts 4 }

-- newer devices return a sysObjectID value that corresponds to the
-- device model number

ciscoIGS  OBJECT IDENTIFIER
    ::= { ciscoProducts 5 }

cisco3000  OBJECT IDENTIFIER
    ::= { ciscoProducts 6 }

cisco4000  OBJECT IDENTIFIER
    ::= { ciscoProducts 7 }

cisco7000  OBJECT IDENTIFIER
    ::= { ciscoProducts 8 }

ciscoCS500  OBJECT IDENTIFIER
    ::= { ciscoProducts 9 }

cisco2000  OBJECT IDENTIFIER
    ::= { ciscoProducts 10 }

-- note well that an AGS+ must contain a cBus controller in order to
-- know that it is an AGS+, otherwise it is unable to determine what
-- kind of device it is, and returns one of the functionality-based
-- sysObjectID values from above

ciscoAGSplus  OBJECT IDENTIFIER
    ::= { ciscoProducts 11 }

cisco7010  OBJECT IDENTIFIER
    ::= { ciscoProducts 12 }

cisco2500  OBJECT IDENTIFIER
    ::= { ciscoProducts 13 }

cisco4500  OBJECT IDENTIFIER
    ::= { ciscoProducts 14 }

cisco2102  OBJECT IDENTIFIER
    ::= { ciscoProducts 15 }

cisco2202  OBJECT IDENTIFIER
    ::= { ciscoProducts 16 }

cisco2501  OBJECT IDENTIFIER
    ::= { ciscoProducts 17 }

cisco2502  OBJECT IDENTIFIER
    ::= { ciscoProducts 18 }

cisco2503  OBJECT IDENTIFIER
    ::= { ciscoProducts 19 }

cisco2504  OBJECT IDENTIFIER
    ::= { ciscoProducts 20 }

cisco2505  OBJECT IDENTIFIER
    ::= { ciscoProducts 21 }

cisco2506  OBJECT IDENTIFIER
    ::= { ciscoProducts 22 }

cisco2507  OBJECT IDENTIFIER
    ::= { ciscoProducts 23 }

cisco2508  OBJECT IDENTIFIER
    ::= { ciscoProducts 24 }

cisco2509  OBJECT IDENTIFIER
    ::= { ciscoProducts 25 }

cisco2510  OBJECT IDENTIFIER
    ::= { ciscoProducts 26 }

cisco2511  OBJECT IDENTIFIER
    ::= { ciscoProducts 27 }

cisco2512  OBJECT IDENTIFIER
    ::= { ciscoProducts 28 }

cisco2513  OBJECT IDENTIFIER
    ::= { ciscoProducts 29 }

cisco2514  OBJECT IDENTIFIER
    ::= { ciscoProducts 30 }

cisco2515  OBJECT IDENTIFIER
    ::= { ciscoProducts 31 }

cisco3101  OBJECT IDENTIFIER
    ::= { ciscoProducts 32 }

cisco3102  OBJECT IDENTIFIER
    ::= { ciscoProducts 33 }

cisco3103  OBJECT IDENTIFIER
    ::= { ciscoProducts 34 }

cisco3104  OBJECT IDENTIFIER
    ::= { ciscoProducts 35 }

cisco3202  OBJECT IDENTIFIER
    ::= { ciscoProducts 36 }

cisco3204  OBJECT IDENTIFIER
    ::= { ciscoProducts 37 }

ciscoAccessProRC  OBJECT IDENTIFIER
    ::= { ciscoProducts 38 }

ciscoAccessProEC  OBJECT IDENTIFIER
    ::= { ciscoProducts 39 }

cisco1000  OBJECT IDENTIFIER
    ::= { ciscoProducts 40 }

cisco1003  OBJECT IDENTIFIER
    ::= { ciscoProducts 41 }

cisco2516  OBJECT IDENTIFIER
    ::= { ciscoProducts 42 }

cisco1020  OBJECT IDENTIFIER
    ::= { ciscoProducts 43 }

cisco1004  OBJECT IDENTIFIER
    ::= { ciscoProducts 44 }

cisco7507  OBJECT IDENTIFIER
    ::= { ciscoProducts 45 }

cisco7513  OBJECT IDENTIFIER
    ::= { ciscoProducts 46 }

cisco7506  OBJECT IDENTIFIER
    ::= { ciscoProducts 47 }

cisco7505  OBJECT IDENTIFIER
    ::= { ciscoProducts 48 }

cisco1005  OBJECT IDENTIFIER
    ::= { ciscoProducts 49 }

cisco4700  OBJECT IDENTIFIER
    ::= { ciscoProducts 50 }

ciscoPro1003  OBJECT IDENTIFIER
    ::= { ciscoProducts 51 }

ciscoPro1004  OBJECT IDENTIFIER
    ::= { ciscoProducts 52 }

ciscoPro1005  OBJECT IDENTIFIER
    ::= { ciscoProducts 53 }

ciscoPro1020  OBJECT IDENTIFIER
    ::= { ciscoProducts 54 }

ciscoPro2500PCE  OBJECT IDENTIFIER
    ::= { ciscoProducts 55 }

ciscoPro2501  OBJECT IDENTIFIER
    ::= { ciscoProducts 56 }

ciscoPro2503  OBJECT IDENTIFIER
    ::= { ciscoProducts 57 }

ciscoPro2505  OBJECT IDENTIFIER
    ::= { ciscoProducts 58 }

ciscoPro2507  OBJECT IDENTIFIER
    ::= { ciscoProducts 59 }

ciscoPro2509  OBJECT IDENTIFIER
    ::= { ciscoProducts 60 }

ciscoPro2511  OBJECT IDENTIFIER
    ::= { ciscoProducts 61 }

ciscoPro2514  OBJECT IDENTIFIER
    ::= { ciscoProducts 62 }

ciscoPro2516  OBJECT IDENTIFIER
    ::= { ciscoProducts 63 }

ciscoPro2519  OBJECT IDENTIFIER
    ::= { ciscoProducts 64 }

ciscoPro2521  OBJECT IDENTIFIER
    ::= { ciscoProducts 65 }

ciscoPro4500  OBJECT IDENTIFIER
    ::= { ciscoProducts 66 }

cisco2517  OBJECT IDENTIFIER
    ::= { ciscoProducts 67 }

cisco2518  OBJECT IDENTIFIER
    ::= { ciscoProducts 68 }

cisco2519  OBJECT IDENTIFIER
    ::= { ciscoProducts 69 }

cisco2520  OBJECT IDENTIFIER
    ::= { ciscoProducts 70 }

cisco2521  OBJECT IDENTIFIER
    ::= { ciscoProducts 71 }

cisco2522  OBJECT IDENTIFIER
    ::= { ciscoProducts 72 }

cisco2523  OBJECT IDENTIFIER
    ::= { ciscoProducts 73 }

cisco2524  OBJECT IDENTIFIER
    ::= { ciscoProducts 74 }

cisco2525  OBJECT IDENTIFIER
    ::= { ciscoProducts 75 }

ciscoPro751  OBJECT IDENTIFIER
    ::= { ciscoProducts 76 }

ciscoPro752  OBJECT IDENTIFIER
    ::= { ciscoProducts 77 }

ciscoPro753  OBJECT IDENTIFIER
    ::= { ciscoProducts 78 }

ciscoPro901  OBJECT IDENTIFIER
    ::= { ciscoProducts 79 }


ciscoPro902  OBJECT IDENTIFIER
    ::= { ciscoProducts 80 }


cisco751  OBJECT IDENTIFIER
    ::= { ciscoProducts 81 }

cisco752  OBJECT IDENTIFIER
    ::= { ciscoProducts 82 }

cisco753  OBJECT IDENTIFIER
    ::= { ciscoProducts 83 }

ciscoPro741  OBJECT IDENTIFIER
    ::= { ciscoProducts 84 }

ciscoPro742  OBJECT IDENTIFIER
    ::= { ciscoProducts 85 }

ciscoPro743  OBJECT IDENTIFIER
    ::= { ciscoProducts 86 }

ciscoPro744  OBJECT IDENTIFIER
    ::= { ciscoProducts 87 }

ciscoPro761  OBJECT IDENTIFIER
    ::= { ciscoProducts 88 }

ciscoPro762  OBJECT IDENTIFIER
    ::= { ciscoProducts 89 }

ciscoPro763  OBJECT IDENTIFIER
    ::= { ciscoProducts 90 }


ciscoPro764  OBJECT IDENTIFIER
    ::= { ciscoProducts 91 }


ciscoPro765  OBJECT IDENTIFIER
    ::= { ciscoProducts 92 }

ciscoPro766  OBJECT IDENTIFIER
    ::= { ciscoProducts 93 }

cisco741  OBJECT IDENTIFIER
    ::= { ciscoProducts 94 }

cisco742  OBJECT IDENTIFIER
    ::= { ciscoProducts 95 }

cisco743  OBJECT IDENTIFIER
    ::= { ciscoProducts 96 }

cisco744  OBJECT IDENTIFIER
    ::= { ciscoProducts 97 }

cisco761  OBJECT IDENTIFIER
    ::= { ciscoProducts 98 }

cisco762  OBJECT IDENTIFIER
    ::= { ciscoProducts 99 }

cisco763  OBJECT IDENTIFIER
    ::= { ciscoProducts 100 }


cisco764  OBJECT IDENTIFIER
    ::= { ciscoProducts 101 }


cisco765  OBJECT IDENTIFIER
    ::= { ciscoProducts 102 }

cisco766  OBJECT IDENTIFIER
    ::= { ciscoProducts 103 }

ciscoPro2520  OBJECT IDENTIFIER
    ::= { ciscoProducts 104 }

ciscoPro2522  OBJECT IDENTIFIER
    ::= { ciscoProducts 105 }

ciscoPro2524  OBJECT IDENTIFIER
    ::= { ciscoProducts 106 }

ciscoLS1010  OBJECT IDENTIFIER
    ::= { ciscoProducts 107 }

cisco7206  OBJECT IDENTIFIER
    ::= { ciscoProducts 108 }

ciscoAS5200  OBJECT IDENTIFIER
    ::= { ciscoProducts 109 }

cisco3640  OBJECT IDENTIFIER
    ::= { ciscoProducts 110 }

ciscoCatalyst3500  OBJECT IDENTIFIER
    ::= { ciscoProducts 111 }

ciscoWSX3011  OBJECT IDENTIFIER
    ::= { ciscoProducts 112 }

cisco1601  OBJECT IDENTIFIER
    ::= { ciscoProducts 113 }

cisco1602  OBJECT IDENTIFIER
    ::= { ciscoProducts 114 }

cisco1603  OBJECT IDENTIFIER
    ::= { ciscoProducts 115 }

cisco1604  OBJECT IDENTIFIER
    ::= { ciscoProducts 116 }

ciscoPro1601  OBJECT IDENTIFIER
    ::= { ciscoProducts 117 }

ciscoPro1602  OBJECT IDENTIFIER
    ::= { ciscoProducts 118 }

ciscoPro1603  OBJECT IDENTIFIER
    ::= { ciscoProducts 119 }

ciscoPro1604  OBJECT IDENTIFIER
    ::= { ciscoProducts 120 }

ciscoWSX5301  OBJECT IDENTIFIER
    ::= { ciscoProducts 121 }


cisco3620  OBJECT IDENTIFIER
    ::= { ciscoProducts 122 }

ciscoPro3620  OBJECT IDENTIFIER
    ::= { ciscoProducts 123 }

ciscoPro3640  OBJECT IDENTIFIER
    ::= { ciscoProducts 124 }

cisco7204  OBJECT IDENTIFIER
    ::= { ciscoProducts 125 }

cisco771  OBJECT IDENTIFIER
    ::= { ciscoProducts 126 }

cisco772  OBJECT IDENTIFIER
    ::= { ciscoProducts 127 }

cisco775  OBJECT IDENTIFIER
    ::= { ciscoProducts 128 }

cisco776  OBJECT IDENTIFIER
    ::= { ciscoProducts 129 }

ciscoPro2502  OBJECT IDENTIFIER
    ::= { ciscoProducts 130 }

ciscoPro2504  OBJECT IDENTIFIER
    ::= { ciscoProducts 131 }

ciscoPro2506  OBJECT IDENTIFIER
    ::= { ciscoProducts 132 }

ciscoPro2508  OBJECT IDENTIFIER
    ::= { ciscoProducts 133 }

ciscoPro2510  OBJECT IDENTIFIER
    ::= { ciscoProducts 134 }

ciscoPro2512  OBJECT IDENTIFIER
    ::= { ciscoProducts 135 }

ciscoPro2513  OBJECT IDENTIFIER
    ::= { ciscoProducts 136 }

ciscoPro2515  OBJECT IDENTIFIER
    ::= { ciscoProducts 137 }

ciscoPro2517  OBJECT IDENTIFIER
    ::= { ciscoProducts 138 }

ciscoPro2518  OBJECT IDENTIFIER
    ::= { ciscoProducts 139 }

ciscoPro2523  OBJECT IDENTIFIER
    ::= { ciscoProducts 140 }

ciscoPro2525  OBJECT IDENTIFIER
    ::= { ciscoProducts 141 }

ciscoPro4700  OBJECT IDENTIFIER
    ::= { ciscoProducts 142 }


ciscoPro316T  OBJECT IDENTIFIER
    ::= { ciscoProducts 147 }

ciscoPro316C  OBJECT IDENTIFIER
    ::= { ciscoProducts 148 }

ciscoPro3116  OBJECT IDENTIFIER
    ::= { ciscoProducts 149 }

catalyst116T  OBJECT IDENTIFIER
    ::= { ciscoProducts 150 }

catalyst116C  OBJECT IDENTIFIER
    ::= { ciscoProducts 151 }

catalyst1116  OBJECT IDENTIFIER
    ::= { ciscoProducts 152 }

ciscoAS2509RJ  OBJECT IDENTIFIER
    ::= { ciscoProducts 153 }

ciscoAS2511RJ  OBJECT IDENTIFIER
    ::= { ciscoProducts 154 }


ciscoMC3810  OBJECT IDENTIFIER
    ::= { ciscoProducts 157 }


cisco1503  OBJECT IDENTIFIER
    ::= { ciscoProducts 160 }

cisco1502  OBJECT IDENTIFIER
    ::= { ciscoProducts 161 }

ciscoAS5300  OBJECT IDENTIFIER
    ::= { ciscoProducts 162 }


ciscoLS1015  OBJECT IDENTIFIER
    ::= { ciscoProducts 164 }

cisco2501FRADFX  OBJECT IDENTIFIER
    ::= { ciscoProducts 165 }

cisco2501LANFRADFX  OBJECT IDENTIFIER
    ::= { ciscoProducts 166 }

cisco2502LANFRADFX  OBJECT IDENTIFIER
    ::= { ciscoProducts 167 }

ciscoWSX5302  OBJECT IDENTIFIER
    ::= { ciscoProducts 168 }

ciscoFastHub216T  OBJECT IDENTIFIER
    ::= { ciscoProducts 169 }

catalyst2908xl  OBJECT IDENTIFIER
    ::= { ciscoProducts 170 }

-- Catalyst 2908XL switch with 8 10/100BaseTX ports

catalyst2916m-xl  OBJECT IDENTIFIER
    ::= { ciscoProducts 171 }

-- Catalyst 2916M-XL switch with 16 10/100BaseTX ports and 2 uplink slots

cisco1605  OBJECT IDENTIFIER
    ::= { ciscoProducts 172 }

cisco12012  OBJECT IDENTIFIER
    ::= { ciscoProducts 173 }


catalyst1912C  OBJECT IDENTIFIER
    ::= { ciscoProducts 175 }

ciscoMicroWebServer2  OBJECT IDENTIFIER
    ::= { ciscoProducts 176 }

ciscoFastHubBMMTX  OBJECT IDENTIFIER
    ::= { ciscoProducts 177 }

ciscoFastHubBMMFX  OBJECT IDENTIFIER
    ::= { ciscoProducts 178 }

ciscoUBR7246  OBJECT IDENTIFIER
    ::= { ciscoProducts 179 }

-- Universal Broadband Router

cisco6400  OBJECT IDENTIFIER
    ::= { ciscoProducts 180 }

cisco12004  OBJECT IDENTIFIER
    ::= { ciscoProducts 181 }

cisco12008  OBJECT IDENTIFIER
    ::= { ciscoProducts 182 }

catalyst2924XL  OBJECT IDENTIFIER
    ::= { ciscoProducts 183 }

-- Catalyst 2924XL switch with 24 10/100BaseTX ports; doesn't support port-based VLANs.

catalyst2924CXL  OBJECT IDENTIFIER
    ::= { ciscoProducts 184 }

-- Catalyst 2924C-XL switch; doesn't support port-based VLANs.

cisco2610  OBJECT IDENTIFIER
    ::= { ciscoProducts 185 }

-- Cisco 2600 platform with 1 integrated ethernet interface

cisco2611  OBJECT IDENTIFIER
    ::= { ciscoProducts 186 }

-- Cisco 2600 platform with 2 integrated ethernet interfaces

cisco2612  OBJECT IDENTIFIER
    ::= { ciscoProducts 187 }

-- Cisco 2600 platform with an integrated ethernet and token ring

ciscoAS5800  OBJECT IDENTIFIER
    ::= { ciscoProducts 188 }

ciscoSC3640  OBJECT IDENTIFIER
    ::= { ciscoProducts 189 }

cisco8510  OBJECT IDENTIFIER
    ::= { ciscoProducts 190 }

-- Cisco Catalyst 8510CSR (Campus Switching Router)

ciscoUBR904  OBJECT IDENTIFIER
    ::= { ciscoProducts 191 }

-- Cisco Cable Modem (UBR - Universal Broadband Router)

cisco6200  OBJECT IDENTIFIER
    ::= { ciscoProducts 192 }


cisco7202  OBJECT IDENTIFIER
    ::= { ciscoProducts 194 }

-- Modular two slot router in the cisco7200 family

cisco2613  OBJECT IDENTIFIER
    ::= { ciscoProducts 195 }

-- Cisco 2600 platform with 1 integrated token ring interface

cisco8515  OBJECT IDENTIFIER
    ::= { ciscoProducts 196 }

-- Cisco Catalyst 8515CSR (Campus Switching Router)

catalyst9006  OBJECT IDENTIFIER
    ::= { ciscoProducts 197 }

catalyst9009  OBJECT IDENTIFIER
    ::= { ciscoProducts 198 }

ciscoRPM  OBJECT IDENTIFIER
    ::= { ciscoProducts 199 }

-- Router Processor Module

cisco1710  OBJECT IDENTIFIER
    ::= { ciscoProducts 200 }

-- VPN(Virtual Private Network) Security Router with 1 FastEthernet and 1 Ethernet interface onboard

cisco1720  OBJECT IDENTIFIER
    ::= { ciscoProducts 201 }

catalyst8540msr  OBJECT IDENTIFIER
    ::= { ciscoProducts 202 }

-- Catalyst 8540 Multiservice Switching Router

catalyst8540csr  OBJECT IDENTIFIER
    ::= { ciscoProducts 203 }

-- Catalyst 8540 Campus Switching Router

cisco7576  OBJECT IDENTIFIER
    ::= { ciscoProducts 204 }

-- Dual Independent RSP platform, 13 slots

cisco3660  OBJECT IDENTIFIER
    ::= { ciscoProducts 205 }

-- Six slot MARs router

cisco1401  OBJECT IDENTIFIER
    ::= { ciscoProducts 206 }

-- Router product with 1 ethernet and 1 ATM25 interface

cisco2620  OBJECT IDENTIFIER
    ::= { ciscoProducts 208 }

-- Cisco 2600 chassis with 1 onboard FE

cisco2621  OBJECT IDENTIFIER
    ::= { ciscoProducts 209 }

-- Cisco 2600 chassis with 2 onboard 10/100 FE ports

ciscoUBR7223  OBJECT IDENTIFIER
    ::= { ciscoProducts 210 }

-- Universal Broadband Router

cisco6400Nrp  OBJECT IDENTIFIER
    ::= { ciscoProducts 211 }

-- Cisco 6400 Network Routing Processor

cisco801  OBJECT IDENTIFIER
    ::= { ciscoProducts 212 }

-- Cisco 800 platform with 1 ethernet and 1 BRI S/T

cisco802  OBJECT IDENTIFIER
    ::= { ciscoProducts 213 }

-- Cisco 800 platform with 1 ethernet and 1 BRI U

cisco803  OBJECT IDENTIFIER
    ::= { ciscoProducts 214 }

-- Cisco 800 platform with 1 ethernet 4-port HUB, 1 BRI S/T, and 2 POTs

cisco804  OBJECT IDENTIFIER
    ::= { ciscoProducts 215 }

-- Cisco 800 platform with 1 ethernet 4-port HUB, 1 BRI U, and 2 POTs

cisco1750  OBJECT IDENTIFIER
    ::= { ciscoProducts 216 }

-- VoIP (Voice over IP) capable Cisco 1700 platform with 2 WIC/VIC slots and 1 VIC-only slot

catalyst2924XLv  OBJECT IDENTIFIER
    ::= { ciscoProducts 217 }

-- Catalyst 2924XL switch with 24 10BaseT/100BaseTX autosensing switch ports; supports port-based VLANs; can run Standard or Enterprise edition software.

catalyst2924CXLv  OBJECT IDENTIFIER
    ::= { ciscoProducts 218 }

-- Catalyst 2924C-XL switch with 22 10BaseT/100BaseTX and 2 100BaseFX autosensing switch ports; supports port-based VLANs; can run Standard or Enterprise edition software.

catalyst2912XL  OBJECT IDENTIFIER
    ::= { ciscoProducts 219 }

-- Catalyst 2912XL switch with 12 autosensing 10/100BaseTX ports, can run Standard or Enterprise edition software.

catalyst2924MXL  OBJECT IDENTIFIER
    ::= { ciscoProducts 220 }

-- Catalyst 2924M-XL switch with 24 autosensing 10/100BaseTX ports and 2 uplink slots, can run Standard or Enterprise edition software.

catalyst2912MfXL  OBJECT IDENTIFIER
    ::= { ciscoProducts 221 }

-- Catalyst 2912MF-XL switch with 12 100BaseFX ports and 2 uplink slots; can only run Enterprise edition software.

cisco7206VXR  OBJECT IDENTIFIER
    ::= { ciscoProducts 222 }

-- Cisco 7200 platform, VXR series chassis with 6 slots

cisco7204VXR  OBJECT IDENTIFIER
    ::= { ciscoProducts 223 }

-- Cisco 7200 platform, VXR series chassis with 4 slots

cisco1538M  OBJECT IDENTIFIER
    ::= { ciscoProducts 224 }

-- Cisco Network Office 8-port 10/100 Repeater

cisco1548M  OBJECT IDENTIFIER
    ::= { ciscoProducts 225 }

-- Cisco Network Office 10/100 Switch

ciscoFasthub100  OBJECT IDENTIFIER
    ::= { ciscoProducts 226 }

-- Cisco Fast Hub 100 Series 10/100 Repeater

ciscoPIXFirewall  OBJECT IDENTIFIER
    ::= { ciscoProducts 227 }

-- Cisco PIX Firewall

ciscoMGX8850  OBJECT IDENTIFIER
    ::= { ciscoProducts 228 }

-- Cisco Multiservice Gigabit Switch with 32 half height slots

ciscoMGX8830  OBJECT IDENTIFIER
    ::= { ciscoProducts 229 }

-- Cisco Multiservice Switch with 16 half-height slots
-- ciscoMGX8820 OBJECT IDENTIFIER ::= { ciscoProducts 229 }

catalyst8510msr  OBJECT IDENTIFIER
    ::= { ciscoProducts 230 }

-- Catalyst ATM 8510 Multiservice Switching Router

catalyst8515msr  OBJECT IDENTIFIER
    ::= { ciscoProducts 231 }

-- Catalyst ATM 8515 Multiservice Switching Router

ciscoIGX8410  OBJECT IDENTIFIER
    ::= { ciscoProducts 232 }

-- Cisco IGX8400 (Integrated Gigabit eXchange) series wide-area switch with 8 slots

ciscoIGX8420  OBJECT IDENTIFIER
    ::= { ciscoProducts 233 }

-- Cisco IGX8400 (Integrated Gigabit eXchange) series wide-area switch with 16 slots

ciscoIGX8430  OBJECT IDENTIFIER
    ::= { ciscoProducts 234 }

-- Cisco IGX8400 (Integrated Gigabit eXchange) series wide-area switch with 32 slots

ciscoIGX8450  OBJECT IDENTIFIER
    ::= { ciscoProducts 235 }

-- Cisco IGX8400 (Integrated Gigabit eXchange) series wide-area switch with integrated MGX feeder

ciscoBPX8620  OBJECT IDENTIFIER
    ::= { ciscoProducts 237 }

-- Cisco BPX8600 (Broadband Packet eXchange) series basic wide-area switch with 15 slots

ciscoBPX8650  OBJECT IDENTIFIER
    ::= { ciscoProducts 238 }

-- Cisco BPX8600 (Broadband Packet eXchange) series wide-area switch with integrated tag switching controller and 15 slots

ciscoBPX8680  OBJECT IDENTIFIER
    ::= { ciscoProducts 239 }

-- Cisco BPX8600 (Broadband Packet eXchange) series wide-area switch with integrated MGX feeder and 15 slots

ciscoCacheEngine  OBJECT IDENTIFIER
    ::= { ciscoProducts 240 }

-- Cisco Cache Engine

ciscoCat6000  OBJECT IDENTIFIER
    ::= { ciscoProducts 241 }

-- Cisco Catalyst 6000

ciscoBPXSes  OBJECT IDENTIFIER
    ::= { ciscoProducts 242 }

-- Cisco BPX (Broadband Packet eXchange) Service Expansion Slot controller

ciscoIGXSes  OBJECT IDENTIFIER
    ::= { ciscoProducts 243 }

-- Cisco IGX (Integrated Gigabit eXchange) Service Expansion Slot controller/feeder, used in IGX8410/IGX8420/IGX8430 switches.

ciscoLocalDirector  OBJECT IDENTIFIER
    ::= { ciscoProducts 244 }

-- Cisco Local Director

cisco805  OBJECT IDENTIFIER
    ::= { ciscoProducts 245 }

-- Cisco 800 platform with 1 ethernet and 1 serial WIC

catalyst3508GXL  OBJECT IDENTIFIER
    ::= { ciscoProducts 246 }

-- Cisco Catalyst 3508G-XL switch with 8 GBIC Gigabit ports, can run Standard or Enterprise edition software.

catalyst3512XL  OBJECT IDENTIFIER
    ::= { ciscoProducts 247 }

-- Cisco Catalyst 3512XL switch with 12 10/100BaseTX ports and 2 GBIC Gigabit ports, can run Standard or Enterprise edition software.

catalyst3524XL  OBJECT IDENTIFIER
    ::= { ciscoProducts 248 }

-- Cisco Catalyst 3524XL switch with 24 10/100BaseTX ports and 2 GBIC Gigabit ports, can run Standard or Enterprise edition software.

cisco1407  OBJECT IDENTIFIER
    ::= { ciscoProducts 249 }

-- Cisco 1400 series router with 1 Ethernet and 1 ADSL interface, with 1407 chipset

cisco1417  OBJECT IDENTIFIER
    ::= { ciscoProducts 250 }

-- Cisco 1400 series router with 1 Ethernet and 1 ADSL interface, with 1417 chipset

cisco6100  OBJECT IDENTIFIER
    ::= { ciscoProducts 251 }

-- Cisco 6100 DSLAM Chassis

cisco6130  OBJECT IDENTIFIER
    ::= { ciscoProducts 252 }

-- Cisco 6130 DSLAM Chassis

cisco6260  OBJECT IDENTIFIER
    ::= { ciscoProducts 253 }

-- Cisco 6260 DSLAM Chassis

ciscoOpticalRegenerator  OBJECT IDENTIFIER
    ::= { ciscoProducts 254 }

-- Cisco Optical Regenerator

ciscoUBR924  OBJECT IDENTIFIER
    ::= { ciscoProducts 255 }

-- Cisco UBR Cable Modem which is a UBR904 with 2 FXS Voice ports

ciscoWSX6302Msm  OBJECT IDENTIFIER
    ::= { ciscoProducts 256 }

-- Catalyst 6000 or 6500 Series Multilayer Switch Module WS-X6302-MSM that directly interfaces to the switch's backplane to provide layer 3 switching.

catalyst5kRsfc  OBJECT IDENTIFIER
    ::= { ciscoProducts 257 }

-- Router Switching Feature Card for the Catalyst 5000 that is treated as a standalone system by the NMS

catalyst6kMsfc  OBJECT IDENTIFIER
    ::= { ciscoProducts 258 }

-- Multilevel Switching Feature Card for Catalyst 6000 that is treated as a standalone system by the NMS

cisco7120Quadt1  OBJECT IDENTIFIER
    ::= { ciscoProducts 259 }

-- 7120 Series chassis with 2 10/100 FE interfaces, 4 T1/E1 interfaces

cisco7120T3  OBJECT IDENTIFIER
    ::= { ciscoProducts 260 }

-- 7120 Series chassis with 2 10/100 FE interfaces, 1 T3 interface

cisco7120E3  OBJECT IDENTIFIER
    ::= { ciscoProducts 261 }

-- 7120 Series chassis with 2 10/100 FE interfaces, 1 E3 interface

cisco7120At3  OBJECT IDENTIFIER
    ::= { ciscoProducts 262 }

-- 7120 Series chassis with 2 10/100 FE interfaces, 1 T3 ATM interface

cisco7120Ae3  OBJECT IDENTIFIER
    ::= { ciscoProducts 263 }

-- 7120 Series chassis with 2 10/100 FE interfaces, 1 E3 ATM interface

cisco7120Smi3  OBJECT IDENTIFIER
    ::= { ciscoProducts 264 }

-- 7120 Series chassis with 2 10/100 FE interfaces, 1 OC3SMI ATM interface

cisco7140Dualt3  OBJECT IDENTIFIER
    ::= { ciscoProducts 265 }

-- 7140 Series chassis with 2 10/100 FE interfaces, 2 T3 interfaces

cisco7140Duale3  OBJECT IDENTIFIER
    ::= { ciscoProducts 266 }

-- 7140 Series chassis with 2 10/100 FE interfaces, 2 E3 interfaces

cisco7140Dualat3  OBJECT IDENTIFIER
    ::= { ciscoProducts 267 }

-- 7140 Series chassis with 2 10/100 FE interfaces, 2 T3 ATM interfaces

cisco7140Dualae3  OBJECT IDENTIFIER
    ::= { ciscoProducts 268 }

-- 7140 Series chassis with 2 10/100 FE interfaces, 2 E3 ATM interfaces

cisco7140Dualmm3  OBJECT IDENTIFIER
    ::= { ciscoProducts 269 }

-- 7140 Series chassis with 2 10/100 FE interfaces, 2 OC3MM ATM interfaces

cisco827QuadV  OBJECT IDENTIFIER
    ::= { ciscoProducts 270 }

-- Cisco 800 platform with 1 ethernet, 1 ADSL DMT issue 2, and 4 voice POTS FXS ports

ciscoUBR7246VXR  OBJECT IDENTIFIER
    ::= { ciscoProducts 271 }

-- Cisco 7246 Universal Broadband Router, VXR series

cisco10400  OBJECT IDENTIFIER
    ::= { ciscoProducts 272 }

-- Cisco 10000 platform with 10 slots

cisco12016  OBJECT IDENTIFIER
    ::= { ciscoProducts 273 }

-- Cisco 12000 platform with 16 slots

ciscoAs5400  OBJECT IDENTIFIER
    ::= { ciscoProducts 274 }

-- Cisco AS5400 platform

cat2948gL3  OBJECT IDENTIFIER
    ::= { ciscoProducts 275 }

-- Cisco Catalyst WS-C2948G-L3 48 port 10/100 Layer 3 switch with 2 GBIC ports

cisco7140Octt1  OBJECT IDENTIFIER
    ::= { ciscoProducts 276 }

-- 7140 Series chassis with 8 integrated T1/E1 serial ports

cisco7140Dualfe  OBJECT IDENTIFIER
    ::= { ciscoProducts 277 }

-- 7140 Series chassis with 2 integrated 10/100 FE interfaces

cat3548XL  OBJECT IDENTIFIER
    ::= { ciscoProducts 278 }

-- Catalyst 3548XL switch (WS-C3548-XL)

ciscoVG200  OBJECT IDENTIFIER
    ::= { ciscoProducts 279 }

-- Cisco Voice Gateway 200 controlled by Cisco Call Manager

cat6006  OBJECT IDENTIFIER
    ::= { ciscoProducts 280 }

-- Catalyst 6000 with 6 slots

cat6009  OBJECT IDENTIFIER
    ::= { ciscoProducts 281 }

-- Catalyst 6000 with 9 slots

cat6506  OBJECT IDENTIFIER
    ::= { ciscoProducts 282 }

-- Catalyst 6000 Plus with 6 slots

cat6509  OBJECT IDENTIFIER
    ::= { ciscoProducts 283 }

-- Catalyst 6000 Plus with 9 slots

cisco827  OBJECT IDENTIFIER
    ::= { ciscoProducts 284 }

-- Cisco 800 platform with 1 ethernet, 1 ADSL DMT issue 2

ciscoManagementEngine1100  OBJECT IDENTIFIER
    ::= { ciscoProducts 285 }

-- Cisco Management Engine 1100 for doing distributed SNMP polling

ciscoMc3810V3  OBJECT IDENTIFIER
    ::= { ciscoProducts 286 }

-- Cisco MC3810-V3, capable of data, voice and video.  Supports 2 additional ports than the MC3810-V, used for optional access cards.

cat3524tXLEn  OBJECT IDENTIFIER
    ::= { ciscoProducts 287 }

-- Cisco Catalyst 3524 switch (WS-C3524T-XL-EN) with 24 10/100 ports and 2 GBIC gigabit ports.  Runs Enterprise edition software and provides telephony power to attached IP telephones

cisco7507z  OBJECT IDENTIFIER
    ::= { ciscoProducts 288 }

-- Cisco 7507z chassis, Czbus capable, 7 slots

cisco7513z  OBJECT IDENTIFIER
    ::= { ciscoProducts 289 }

-- Cisco 7513z chassis, Czbus capable, 13 slots

cisco7507mx  OBJECT IDENTIFIER
    ::= { ciscoProducts 290 }

-- Cisco 7507mx chassis, Czbus capable, TDM (Time Division Multiplexing) backplane support, 7 slots

cisco7513mx  OBJECT IDENTIFIER
    ::= { ciscoProducts 291 }

-- Cisco 7513mx chassis, Czbus capable, TDM (Time Division Multiplexing) backplane support, 13 slots

ciscoUBR912C  OBJECT IDENTIFIER
    ::= { ciscoProducts 292 }

-- Cisco uBR912-C Cable Modem with CSU/DSU WIC

ciscoUBR912S  OBJECT IDENTIFIER
    ::= { ciscoProducts 293 }

-- Cisco uBR912-S Cable Modem with Serial WIC

ciscoUBR914  OBJECT IDENTIFIER
    ::= { ciscoProducts 294 }

-- Cisco uBR914 Cable Modem with removable WIC

cisco802J  OBJECT IDENTIFIER
    ::= { ciscoProducts 295 }

-- Cisco 800 platform with 1 ethernet, 1 BRI S/T, and 1 Japanese BRI U

cisco804J  OBJECT IDENTIFIER
    ::= { ciscoProducts 296 }

-- Cisco 800 platform with 1 ethernet, 2 POTS, 1 BRI/ST, and 1 Japanese BRI U

cisco6160  OBJECT IDENTIFIER
    ::= { ciscoProducts 297 }

-- Cisco 6160 DSLAM chassis

cat4908gL3  OBJECT IDENTIFIER
    ::= { ciscoProducts 298 }

-- Catalyst 4908G-L3 (WS-C4908G-L3) Mid-range fixed configuration layer 3 switch with 6 GBIC based Gigabit Ethernet ports

cisco6015  OBJECT IDENTIFIER
    ::= { ciscoProducts 299 }

-- Cisco 6015 DSLAM chassis

cat4232L3  OBJECT IDENTIFIER
    ::= { ciscoProducts 300 }

-- Cisco Catalyst 4232-L3 layer 3 line card that is treated as a standalone system by the NMS

catalyst6kMsfc2  OBJECT IDENTIFIER
    ::= { ciscoProducts 301 }

-- Multilevel Switching Feature Card Version 2 for Catalyst 6000 that is treated as a standalone system by the NMS

cisco7750Mrp200  OBJECT IDENTIFIER
    ::= { ciscoProducts 302 }

-- Cisco ICS 7750 Multiservice Route Processor 200

cisco7750Ssp80  OBJECT IDENTIFIER
    ::= { ciscoProducts 303 }

-- Cisco ICS 7750 System Switch Processor 80

ciscoMGX8230  OBJECT IDENTIFIER
    ::= { ciscoProducts 304 }

-- Multi Service Switch with 16 half-height slots

ciscoMGX8250  OBJECT IDENTIFIER
    ::= { ciscoProducts 305 }

-- Multi Service Switch with 32 half-height slots

ciscoCVA122  OBJECT IDENTIFIER
    ::= { ciscoProducts 306 }

-- Cisco CVA122 Cable Voice Adapter (Residential Cable Modem with two Voice Ports)

ciscoCVA124  OBJECT IDENTIFIER
    ::= { ciscoProducts 307 }

-- Cisco CVA124 Cable Voice Adapter (Residential Cable Modem with four Voice Ports)

ciscoAs5850  OBJECT IDENTIFIER
    ::= { ciscoProducts 308 }

-- High End Dial Access Server

cat6509Sp  OBJECT IDENTIFIER
    ::= { ciscoProducts 310 }

-- 9-slot Constellation+ vertical slot chassis

ciscoMGX8240  OBJECT IDENTIFIER
    ::= { ciscoProducts 311 }

-- High Density Circuit Emulation Service Gateway for Private Line Service

cat4840gL3  OBJECT IDENTIFIER
    ::= { ciscoProducts 312 }

-- Catalyst 4840G-L3 (WS-C4840G) Layer 3 Ethernet Switching System with Server Load Balancing

ciscoAS5350  OBJECT IDENTIFIER
    ::= { ciscoProducts 313 }

-- Cisco low end Access server platform

cisco7750  OBJECT IDENTIFIER
    ::= { ciscoProducts 314 }

-- Cisco Integrated Communication System (ICS) 7750

ciscoMGX8950  OBJECT IDENTIFIER
    ::= { ciscoProducts 315 }

-- Multiservice Gigabit Switch(180Gb switch) with 32 half height slots

ciscoUBR925  OBJECT IDENTIFIER
    ::= { ciscoProducts 316 }

-- Cisco UBR925 Cable Modem/Router with VOIP and hardware accelerated IPSEC

ciscoUBR10012  OBJECT IDENTIFIER
    ::= { ciscoProducts 317 }

-- Cisco uBR10000 platform with 8 broadband slots and 4 WAN slots

catalyst4kGateway  OBJECT IDENTIFIER
    ::= { ciscoProducts 318 }

-- Catalyst 4000 Access Gateway line card supporting voice and WAN (Wide Area Network) interfaces as well as conferencing and transcoding services for operation with the Cisco Call Manager

cisco2650  OBJECT IDENTIFIER
    ::= { ciscoProducts 319 }

-- c2650 platform with 1 integrated fast ethernet interface

cisco2651  OBJECT IDENTIFIER
    ::= { ciscoProducts 320 }

-- c2650 platform with 2 integrated fast ethernet interfaces

cisco826QuadV  OBJECT IDENTIFIER
    ::= { ciscoProducts 321 }

-- Cisco 800 platform with 1 ethernet, 1 ADSL over ISDN and 4 voice POTS FXS ports

cisco826  OBJECT IDENTIFIER
    ::= { ciscoProducts 322 }

-- Cisco 800 platform with 1 ethernet, 1 ADSL over ISDN

catalyst295012  OBJECT IDENTIFIER
    ::= { ciscoProducts 323 }

-- Cisco Catalyst c2950 switch  with 12 10/100BaseTX ports (WS-c2950-12)

catalyst295024  OBJECT IDENTIFIER
    ::= { ciscoProducts 324 }

-- Cisco Catalyst c2950 switch with 24 10/100 BaseTX ports (WS-c2950-24)

catalyst295024C  OBJECT IDENTIFIER
    ::= { ciscoProducts 325 }

-- Cisco Catalyst c2950 switch with 24 10/100 BaseTX ports and 2 100BASE-FX uplink ports (WS-c2950C-24)

cisco1751  OBJECT IDENTIFIER
    ::= { ciscoProducts 326 }

-- Digital voice capable Cisco 1700 platform with 2 WIC/VIC slots and 1 VIC-only slot

cisco1730Iad8Fxs  OBJECT IDENTIFIER
    ::= { ciscoProducts 327 }


cisco1730Iad16Fxs  OBJECT IDENTIFIER
    ::= { ciscoProducts 328 }


cisco626  OBJECT IDENTIFIER
    ::= { ciscoProducts 329 }

-- Cisco 600 DSL CPE pltaform with ADSL, DMT issue 1, 25M ATM interface

cisco627  OBJECT IDENTIFIER
    ::= { ciscoProducts 330 }

-- Cisco 600 DSL CPE pltaform with ADSL, DMT issue 2, 25M ATM interface

cisco633  OBJECT IDENTIFIER
    ::= { ciscoProducts 331 }

-- Cisco 600 DSL CPE platform with SDSL, 2B1Q line coding, serial interface (V.35/X.21)

cisco673  OBJECT IDENTIFIER
    ::= { ciscoProducts 332 }

-- Cisco 600 DSL CPE platform with SDSL, 2B1Q line coding, ethernet interface

cisco675  OBJECT IDENTIFIER
    ::= { ciscoProducts 333 }

-- Cisco 600 DSL CPE platform with ADSL, CAP, ethernet interface, POTS connector

cisco675e  OBJECT IDENTIFIER
    ::= { ciscoProducts 334 }

-- Cisco 600 DSL CPE platform with ADSL, CAP, ethernet interface, universal power supply

cisco676  OBJECT IDENTIFIER
    ::= { ciscoProducts 335 }

-- Cisco 600 DSL CPE platform with ADSL, DMT issue 1, ethernet interface

cisco677  OBJECT IDENTIFIER
    ::= { ciscoProducts 336 }

-- Cisco 600 DSL CPE platform with ADSL, DMT issue 2, ethernet interface

cisco678  OBJECT IDENTIFIER
    ::= { ciscoProducts 337 }

-- Cisco 600 DSL CPE platform with ADSL, CAP/DMT/G.Lite, ethernet interface

cisco3661Ac  OBJECT IDENTIFIER
    ::= { ciscoProducts 338 }

-- 1 Fast Ethernet version of c3660 with a AC power supply

cisco3661Dc  OBJECT IDENTIFIER
    ::= { ciscoProducts 339 }

-- 1 Fast Ethernet version of c3660 with a DC power supply

cisco3662Ac  OBJECT IDENTIFIER
    ::= { ciscoProducts 340 }

-- 2 Fast Ethernet version of c3660 with a AC power supply

cisco3662Dc  OBJECT IDENTIFIER
    ::= { ciscoProducts 341 }

-- 2 Fast Ethernet version of c3660 with a DC power supply

cisco3662AcCo  OBJECT IDENTIFIER
    ::= { ciscoProducts 342 }

-- 2 Fast Ethernet version of c3660 with a AC power supply for Telco's

cisco3662DcCo  OBJECT IDENTIFIER
    ::= { ciscoProducts 343 }

-- 2 Fast Ethernet version of c3660 with a DC power supply for Telco's

ciscoUBR7111  OBJECT IDENTIFIER
    ::= { ciscoProducts 344 }

-- Low-end version of the Universal Broadband Router with 1 PA slot, 1 fixed RF line card (MC11C) and integrated upconvertor, designed for hotels, MDUs and smaller cable operators

ciscoUBR7111E  OBJECT IDENTIFIER
    ::= { ciscoProducts 345 }

-- Low-end version of the Universal Broadband Router with 1 PA slot, 1 fixed RF line card (MC11E) and integrated upconvertor, designed for hotels, MDUs and smaller cable operators

ciscoUBR7114  OBJECT IDENTIFIER
    ::= { ciscoProducts 346 }

-- Low-end version of the Universal Broadband Router with 1 PA slot, 1 fixed RF line card (MC14C) and integrated upconvertor, designed for hotels, MDUs and smaller cable operators

ciscoUBR7114E  OBJECT IDENTIFIER
    ::= { ciscoProducts 347 }

-- Low-end version of the Universal Broadband Router with 1 PA slot, 1 fixed RF line card (MC14E) and integrated upconvertor, designed for hotels, MDUs and smaller cable operators

cisco12010  OBJECT IDENTIFIER
    ::= { ciscoProducts 348 }

-- Cisco 12000 platform with 10 slots

cisco8110  OBJECT IDENTIFIER
    ::= { ciscoProducts 349 }

-- Cisco 8110 (ATM network termination device) with 3 Line Interface module slots

cisco8120  OBJECT IDENTIFIER
    ::= { ciscoProducts 350 }


ciscoUBR905  OBJECT IDENTIFIER
    ::= { ciscoProducts 351 }

-- Cisco uBR905 Cable Modem with hardware accelerated IPSEC

ciscoIDS  OBJECT IDENTIFIER
    ::= { ciscoProducts 352 }


ciscoSOHO77  OBJECT IDENTIFIER
    ::= { ciscoProducts 353 }

-- Cisco SOHO (Small Office Home Office) ADSL Router, 1 Ethernet and 1 ADSL G.992.1 (G.DMT) and G.992.2 (G.Lite) Interface

ciscoSOHO76  OBJECT IDENTIFIER
    ::= { ciscoProducts 354 }

-- Cisco SOHO (Small Office Home Office) ADSL over ISDN Router, 1 Ethernet and 1 ADSL ETSI/ITU-T G.992.1 Annex B (G.DMT) Interface

cisco7150Dualfe  OBJECT IDENTIFIER
    ::= { ciscoProducts 355 }

-- 7150 Series chassis with 2 integrated 10/100 FE interfaces

cisco7150Octt1  OBJECT IDENTIFIER
    ::= { ciscoProducts 356 }

-- 7150 Series chassis with 8 integrated T1/E1 serial ports

cisco7150Dualt3  OBJECT IDENTIFIER
    ::= { ciscoProducts 357 }

-- 7150 Series chassis with 2 10/100 FE interfaces, 2 T3 interfaces

ciscoOlympus  OBJECT IDENTIFIER
    ::= { ciscoProducts 358 }

-- Cisco VPN (Virtual Private Network) Router with  4 10/100/1000 Gigabitethernet integrated interfaces

catalyst2950t24  OBJECT IDENTIFIER
    ::= { ciscoProducts 359 }

-- Cisco Catalyst c2950 switch with 24 10/100BaseT ports and 2 10/100/1000BaseT ports

ciscoVPS1110  OBJECT IDENTIFIER
    ::= { ciscoProducts 360 }

-- Cisco VLAN Policy Server 1110 manages VLAN-based policies to control user access to a LAN, leveraging existing authentication mechanisms such as Windows Domain Controllers and Novell's NDS. This policy server is part of CiscoWorks2000 User Registration Tool product.

ciscoContentEngine  OBJECT IDENTIFIER
    ::= { ciscoProducts 361 }

-- Cisco Content Engine.  The Cisco Content Engine is a Content Networking product that accelerates content delivery, ensuring maximum scalability and availability of content.  The Content Engines offer caching, Content Delivery Network (CDN) services, employee internet management (e.g., URL filtering) and proxy services

ciscoIAD2420  OBJECT IDENTIFIER
    ::= { ciscoProducts 362 }

-- Integrated Access Device 2420 (IAD2420) chassis with Analog (8/16) FXS ports with T1 or ADSL (Asymmetrical Digital Subscriber Line) Uplinks

cisco677i  OBJECT IDENTIFIER
    ::= { ciscoProducts 363 }

-- Cisco 600 DSL CPE platform with ASDL, DMT issue 2 over ISDN, ethernet interface

cisco674  OBJECT IDENTIFIER
    ::= { ciscoProducts 364 }

-- Cisco 600 DSL CPE platform with G.SHDSL, ethernet interface

ciscoDPA7630  OBJECT IDENTIFIER
    ::= { ciscoProducts 365 }

-- The Cisco Digital PBX Adapter (DPA) enables the integration of Cisco Call Manager with Octel voice mail systems

catalyst355024  OBJECT IDENTIFIER
    ::= { ciscoProducts 366 }

-- Catalyst 3550 24 10/100 ports + 2 Gig uplinks fixed configuration Layer 2/Layer 3 Ethernet Switch

catalyst355048  OBJECT IDENTIFIER
    ::= { ciscoProducts 367 }

-- Catalyst 3550 48 10/100 ports + 2 Gig uplinks fixed configuration Layer 2/Layer 3 Ethernet Switch

catalyst355012T  OBJECT IDENTIFIER
    ::= { ciscoProducts 368 }

-- Catalyst 3550 12 1000T ports fixed configuration Layer 2/Layer 3 Ethernet Switch

catalyst2924LREXL  OBJECT IDENTIFIER
    ::= { ciscoProducts 369 }

-- Cisco Catalyst c2924XL switch (WS-C2924-LRE-XL) with 24 10BaseS VDSL ports and 4 10/100BaseTX ports

catalyst2912LREXL  OBJECT IDENTIFIER
    ::= { ciscoProducts 370 }

-- Cisco Catalyst c2912XL switch (WS-C2912-LRE-XL) with 12 10BaseS VDSL ports and 4 10/100BaseTX ports

ciscoCVA122E  OBJECT IDENTIFIER
    ::= { ciscoProducts 371 }

-- Cisco CVA122-e Cable Voice Adapter(Residential Cable Modem with two voice ports)- European version

ciscoCVA124E  OBJECT IDENTIFIER
    ::= { ciscoProducts 372 }

-- Cisco CVA124-e Cable Voice Adapter(Residential Cable Modem with four voice ports)- European version

ciscoURM  OBJECT IDENTIFIER
    ::= { ciscoProducts 373 }

-- Universal Router Module for the IGX platform

ciscoURM2FE  OBJECT IDENTIFIER
    ::= { ciscoProducts 374 }

-- Universal router module with 2 Fast Ethernet interfaces for IGX platform

ciscoURM2FE2V  OBJECT IDENTIFIER
    ::= { ciscoProducts 375 }

-- Universal Router Module, with 2 Fast Ethernet ports, and 2 digital voice ports (T1 or E1)

cisco7401VXR  OBJECT IDENTIFIER
    ::= { ciscoProducts 376 }

-- Cisco 7400 Family, 1 Slot router

cisco951  OBJECT IDENTIFIER
    ::= { ciscoProducts 377 }


cisco952  OBJECT IDENTIFIER
    ::= { ciscoProducts 378 }


ciscoCAP340  OBJECT IDENTIFIER
    ::= { ciscoProducts 379 }

-- Aironet Wireless LAN Access Point 340 series

ciscoCAP350  OBJECT IDENTIFIER
    ::= { ciscoProducts 380 }

-- Cisco Wireless LAN Access Point 350 series

ciscoDPA7610  OBJECT IDENTIFIER
    ::= { ciscoProducts 381 }

-- The Cisco Digital PBX Adapter (DPA) enables the integration of Cisco Call Manager with Octel voice mail systems.

cisco828  OBJECT IDENTIFIER
    ::= { ciscoProducts 382 }

-- Cisco 800 platform with 1 Ethernet, 1 G.991.2 (G.shdsl) Interface, data only model

ciscoSOHO78  OBJECT IDENTIFIER
    ::= { ciscoProducts 383 }


cisco806  OBJECT IDENTIFIER
    ::= { ciscoProducts 384 }

-- Cisco SOHO (Small Office Home Office) router with 4 hubbed 10BaseT Ethernet LAN interfaces and 1 10BaseT Ethernet WAN interface

cisco12416  OBJECT IDENTIFIER
    ::= { ciscoProducts 385 }

-- Cisco 12000 platform with 16 slots and 10G fabric card

cat2948gL3Dc  OBJECT IDENTIFIER
    ::= { ciscoProducts 386 }

-- A fixed-configuration Layer 3 Ethernet switch featuring IP, IPX, and IP mulitcast with 48 10/100BaseTX ports using DC power

cat4908gL3Dc  OBJECT IDENTIFIER
    ::= { ciscoProducts 387 }

-- A fixed-configuration L3 Ethernet switch featuring IP,IPX and IP multicast with 8 GBIC ports using DC power

cisco12406  OBJECT IDENTIFIER
    ::= { ciscoProducts 388 }

-- Cisco 12400 platform with 6 slots

ciscoPIXFirewall506  OBJECT IDENTIFIER
    ::= { ciscoProducts 389 }

-- Cisco PIX Firewall 506

ciscoPIXFirewall515  OBJECT IDENTIFIER
    ::= { ciscoProducts 390 }

-- Cisco PIX Firewall 515

ciscoPIXFirewall520  OBJECT IDENTIFIER
    ::= { ciscoProducts 391 }

-- Cisco PIX Firewall 520

ciscoPIXFirewall525  OBJECT IDENTIFIER
    ::= { ciscoProducts 392 }

-- Cisco PIX Firewall 525

ciscoPIXFirewall535  OBJECT IDENTIFIER
    ::= { ciscoProducts 393 }

-- Cisco PIX Firewall 535

cisco12410  OBJECT IDENTIFIER
    ::= { ciscoProducts 394 }

-- Cisco 12410 platform with 10 slots

cisco811  OBJECT IDENTIFIER
    ::= { ciscoProducts 395 }

-- ISDN router for Japan with 1 10BaseT Ethernet port, 1 ISDN BRI(Basic Rate Interface) U, integrated DSU(Data Service Unit)

cisco813  OBJECT IDENTIFIER
    ::= { ciscoProducts 396 }

-- ISDN router forJapan with 10 BaseT 4 ports hub , 1 ISDN BRI(Basic Rate Interface) U, integrated DSU(Data Service Unit) and 2 RJ-11

cisco10720  OBJECT IDENTIFIER
    ::= { ciscoProducts 397 }

-- IP + Optical Access Router

ciscoMWR1900  OBJECT IDENTIFIER
    ::= { ciscoProducts 398 }

-- The Mobile Wireless router is a router targeted at application in a cell site Base Transciever Station (BTS) providing T1/E1 backhaul connections to the aggregation node in Radio Access Networks (RAN)

cisco4224  OBJECT IDENTIFIER
    ::= { ciscoProducts 399 }

-- A standalone 24 port powered Ethernet switch, router and voice gateway

ciscoWSC6513  OBJECT IDENTIFIER
    ::= { ciscoProducts 400 }

-- Catalyst 6000 series chassis with 13 slots

cisco7603  OBJECT IDENTIFIER
    ::= { ciscoProducts 401 }

-- Cisco Optical Services Router 7600 Series Chassis with 3 slots

cisco7606  OBJECT IDENTIFIER
    ::= { ciscoProducts 402 }

-- Cisco Optical Services Router 7600 Series Chassis with 6 slots

cisco7401ASR  OBJECT IDENTIFIER
    ::= { ciscoProducts 403 }

-- Cisco 7400 platform, ASR series with 1 slot

ciscoVG248  OBJECT IDENTIFIER
    ::= { ciscoProducts 404 }

-- Cisco VoIP Voice Gateway for connecting analog telephones fax machines to a Cisco Call Manager based system

ciscoHSE  OBJECT IDENTIFIER
    ::= { ciscoProducts 405 }

-- Cisco Hosting Solution Engine 1105 manages Cisco powered data centers and Points of Presence with routers, switches, server load balancers, firewalls, intrusion detection systems and other layer 4-7 content delivery products

ciscoONS15540ESP  OBJECT IDENTIFIER
    ::= { ciscoProducts 406 }

-- Cisco ONS 15540 Extended Services Platform

ciscoSN5420  OBJECT IDENTIFIER
    ::= { ciscoProducts 407 }

-- SRBU Storage Router 1 Fiber Channel port, 1 Gigabit Ethernet port

ciscoIcs7750Ce300  OBJECT IDENTIFIER
    ::= { ciscoProducts 408 }


ciscoCe507  OBJECT IDENTIFIER
    ::= { ciscoProducts 409 }

-- Cisco Content Engine Model 507

ciscoCe560  OBJECT IDENTIFIER
    ::= { ciscoProducts 410 }

-- Cisco Content Engine Model 560

ciscoCe590  OBJECT IDENTIFIER
    ::= { ciscoProducts 411 }

-- Cisco Content Engine Model 590

ciscoCe7320  OBJECT IDENTIFIER
    ::= { ciscoProducts 412 }

-- Cisco Content Engine Model 7320

cisco2691  OBJECT IDENTIFIER
    ::= { ciscoProducts 413 }

-- One Network Module slot, three WIC slot, two Fast Ethernet port MARS router

cisco3725  OBJECT IDENTIFIER
    ::= { ciscoProducts 414 }

-- Two Network Module slot, three WIC slot, two Fast Ethernet port MARS router

cisco3640A  OBJECT IDENTIFIER
    ::= { ciscoProducts 415 }


cisco1760  OBJECT IDENTIFIER
    ::= { ciscoProducts 416 }

-- Analog/digital voice capable, 19" rack-mount (1RU) Cisco 1700 platform with 2 WIC/VIC slots and 2 VIC-only slots

ciscoPIXFirewall501  OBJECT IDENTIFIER
    ::= { ciscoProducts 417 }

-- Cisco PIX Firewall 501

cisco2610M  OBJECT IDENTIFIER
    ::= { ciscoProducts 418 }

-- c2600M with 1 integrated ethernet interface

cisco2611M  OBJECT IDENTIFIER
    ::= { ciscoProducts 419 }

-- c2600M with 2 integrated ethernet interfaces

ciscoGP10  OBJECT IDENTIFIER
    ::= { ciscoProducts 420 }


ciscoMC21  OBJECT IDENTIFIER
    ::= { ciscoProducts 421 }


ciscoSN51  OBJECT IDENTIFIER
    ::= { ciscoProducts 422 }


cisco12404  OBJECT IDENTIFIER
    ::= { ciscoProducts 423 }

-- Cisco 12400 platform with 4 slots

cisco9004  OBJECT IDENTIFIER
    ::= { ciscoProducts 424 }

-- Cisco 9000 Chassis

cisco3631Co  OBJECT IDENTIFIER
    ::= { ciscoProducts 425 }

-- Two Network Module Slot , two WIC slot, one Fast Ethernet port MARS router

catalyst295012G  OBJECT IDENTIFIER
    ::= { ciscoProducts 427 }

-- Cisco Catalyst c2950 switch with 12 10/100 BaseTX ports and 2 GBIC (Gigabit Interface Converter) slots (WS-c2950g-12)

catalyst295024G  OBJECT IDENTIFIER
    ::= { ciscoProducts 428 }

-- Cisco Catalyst c2950 switch with 24 10/100 BaseTX ports and 2 GBIC (Gigabit Interface Converter) slots (WS-c2950g-12)

catalyst295048G  OBJECT IDENTIFIER
    ::= { ciscoProducts 429 }

-- isco Catalyst c2950 switch with 48 10/100 BaseTX ports and 2 GBIC (Gigabit Interface Converter) slots (WS-c2950g-12)

catalyst295024S  OBJECT IDENTIFIER
    ::= { ciscoProducts 430 }

-- Cisco Catalyst c2950 switch with 24 10/100 BaseSX ports (Single Mode) and 2 GBIC (Gigabit Interface Converter) slots (WS-c2950g-12)

catalyst355012G  OBJECT IDENTIFIER
    ::= { ciscoProducts 431 }

-- 10 Gig (GBIC) + 2 10/100/1000baseT ports, fixed configuration layer 2/3 Ethernet switch

ciscoCE507AV  OBJECT IDENTIFIER
    ::= { ciscoProducts 432 }

-- Cisco Content Engine Model 507-AV

ciscoCE560AV  OBJECT IDENTIFIER
    ::= { ciscoProducts 433 }

-- Cisco Content Engine Model 560-AV

ciscoIE2105  OBJECT IDENTIFIER
    ::= { ciscoProducts 434 }

-- The Cisco Intelligence Engine 2100 series is a new form of network device that provides intelligent network interface to applications and users

ciscoMGX8850Pxm1E  OBJECT IDENTIFIER
    ::= { ciscoProducts 435 }

-- PXM1E Controller based 32 full-height slot MGX8850

cisco3745  OBJECT IDENTIFIER
    ::= { ciscoProducts 436 }

-- 3700 family four slot modular router

cisco10005  OBJECT IDENTIFIER
    ::= { ciscoProducts 437 }

-- Cisco 10000 platform with 7 slots

cisco10008  OBJECT IDENTIFIER
    ::= { ciscoProducts 438 }

-- Cisco 10000 platform with 10 slots

cisco7304  OBJECT IDENTIFIER
    ::= { ciscoProducts 439 }

-- Cisco 7304 Chassis

ciscoRpmXf  OBJECT IDENTIFIER
    ::= { ciscoProducts 440 }

-- Chassis for RPM-XF router module

ciscoOsm4oc3PosSmIr  OBJECT IDENTIFIER
    ::= { ciscoProducts 441 }


ciscoOsm4oc3PosMmSr  OBJECT IDENTIFIER
    ::= { ciscoProducts 442 }


ciscoOsm4oc3PosSmLr  OBJECT IDENTIFIER
    ::= { ciscoProducts 443 }


cisco1721  OBJECT IDENTIFIER
    ::= { ciscoProducts 444 }

-- Enhanced 1720 with support for onboard Fast Ethernet and 2 WAN Interface cards and optional hardware encryption module

cat4000Sup3  OBJECT IDENTIFIER
    ::= { ciscoProducts 445 }


cisco827H  OBJECT IDENTIFIER
    ::= { ciscoProducts 446 }

-- Cisco 800 platform with 4-port 10Base-T Ethernet, and 1 ADSL over POTS Interface, data only model

ciscoSOHO77H  OBJECT IDENTIFIER
    ::= { ciscoProducts 447 }


cat4006  OBJECT IDENTIFIER
    ::= { ciscoProducts 448 }

-- Catalyst 4000 with 6 slots (WS-C4006)

ciscoWSC6503  OBJECT IDENTIFIER
    ::= { ciscoProducts 449 }

-- Catalyst 6000 series chassis with 3 slots

ciscoPIXFirewall506E  OBJECT IDENTIFIER
    ::= { ciscoProducts 450 }

-- Cisco PIX Firewall 506E

ciscoPIXFirewall515E  OBJECT IDENTIFIER
    ::= { ciscoProducts 451 }

-- Cisco PIX Firewall 515E

cat355024Dc  OBJECT IDENTIFIER
    ::= { ciscoProducts 452 }

-- Catalyst 3550 24 10/100Base-Tx ports + 2 Gig uplinks fixed configuration Layer 2/Layer 3 Ethernet Switch with DC power

cat355024Mmf  OBJECT IDENTIFIER
    ::= { ciscoProducts 453 }

-- Catalyst 3550 24 10/100Mbps Multimode Fiber ports + 2 Gig uplinks fixed configuration Layer 2/Layer 3 Ethernet Switch

ciscoCE2636  OBJECT IDENTIFIER
    ::= { ciscoProducts 454 }

-- Cisco Content Engine Module for 26xx and 36xx series platforms

ciscoDwCE  OBJECT IDENTIFIER
    ::= { ciscoProducts 455 }

-- Double Wide Cisco Content Engine Module for 26xx

cisco7750Mrp300  OBJECT IDENTIFIER
    ::= { ciscoProducts 456 }

-- Cisco ICS 7750 Multiservice Route Processor 300

ciscoRPMPR  OBJECT IDENTIFIER
    ::= { ciscoProducts 457 }

-- For RPM-PR router blade in MGX series switch

cisco14MGX8830Pxm1E  OBJECT IDENTIFIER
    ::= { ciscoProducts 458 }

-- PXM1E Controller based 14 slot MGX8830

ciscoWlse  OBJECT IDENTIFIER
    ::= { ciscoProducts 459 }

-- Wireless LAN Solution Engine

ciscoONS15530  OBJECT IDENTIFIER
    ::= { ciscoProducts 460 }

-- Cisco ONS 15530 platform

ciscoONS15530NEBS  OBJECT IDENTIFIER
    ::= { ciscoProducts 461 }

-- Cisco ONS 15530 Chassis, NEBS compliant

ciscoONS15530ETSI  OBJECT IDENTIFIER
    ::= { ciscoProducts 462 }

-- Cisco ONS 15530 Chassis, ETSI compliant

ciscoSOHO71  OBJECT IDENTIFIER
    ::= { ciscoProducts 463 }


cisco6400UAC  OBJECT IDENTIFIER
    ::= { ciscoProducts 464 }

-- Cisco 6400 Universal Access Concentrator

ciscoAIRAP1200  OBJECT IDENTIFIER
    ::= { ciscoProducts 474 }

-- 1200 series WLAN Access Point with 1 10/100TX port, 1 CardBus slot, 1 Mini PCI slot

ciscoSN5428  OBJECT IDENTIFIER
    ::= { ciscoProducts 475 }

-- Storage Networking 5428 storage router with 2 SFP (Small Form  Factor Pluggable) GBIC Gigabit Ethernet ports and 8 SFP GBIC Fibre Channel ports

cisco2610XM  OBJECT IDENTIFIER
    ::= { ciscoProducts 466 }

-- Cisco c2610XM platform 1 integrated fast ethernet interface with SDRAM

cisco2611XM  OBJECT IDENTIFIER
    ::= { ciscoProducts 467 }

-- Cisco c2611XM platform 2 integrated fast ethernet interfaces with SDRAM

cisco2620XM  OBJECT IDENTIFIER
    ::= { ciscoProducts 468 }

-- Cisco c2620XM platform 1 integrated fast ethernet interface with SDRAM

cisco2621XM  OBJECT IDENTIFIER
    ::= { ciscoProducts 469 }

-- Cisco c2621XM platform 2 integrated fast ethernet interfaces with SDRAM

cisco2650XM  OBJECT IDENTIFIER
    ::= { ciscoProducts 470 }

-- Cisco c2650XM platform 1 integrated fast ethernet interface with SDRAM

cisco2651XM  OBJECT IDENTIFIER
    ::= { ciscoProducts 471 }

-- Cisco c2651XM platform 2 integrated fast ethernet interfaces with SDRAM

catalyst295024GDC  OBJECT IDENTIFIER
    ::= { ciscoProducts 472 }

-- Cisco Catalyst c2950 switch with 24 10/100 BaseTX ports and 2 GBIC (Gigabit Interface Converter) slots and DC power(WS-c2950G-24-DC)

cisco7301  OBJECT IDENTIFIER
    ::= { ciscoProducts 476 }

-- Cisco 7300 platform, 1 Rack Unit (RU) application specific router with 1 slot

cisco12816  OBJECT IDENTIFIER
    ::= { ciscoProducts 477 }

-- Cisco 12816 platform with 16 slots and 40G fabric card

cisco12810  OBJECT IDENTIFIER
    ::= { ciscoProducts 478 }

-- Cisco 12810 platform with 10 slots and 40G fabric card

cisco3250  OBJECT IDENTIFIER
    ::= { ciscoProducts 479 }

-- cisco 3250 mobile Router

catalyst295024SX  OBJECT IDENTIFIER
    ::= { ciscoProducts 480 }

-- Cisco Catalyst c2950 switch with 24 10/100 BaseTX ports and 2 fixed 1000Base Multimode fiber (SX) ports

ciscoONS15540ESPx  OBJECT IDENTIFIER
    ::= { ciscoProducts 481 }

-- Cisco ONS 15540 Extended Services Platform with external optical patch system

catalyst295024LRESt  OBJECT IDENTIFIER
    ::= { ciscoProducts 482 }

-- Cisco Catalyst c2950 switch with 24 10BaseS VDSL Ports and 2 ST ( SFP or 10/100/1000 Base T) (WS-C2950ST-24-LRE)

catalyst29508LRESt  OBJECT IDENTIFIER
    ::= { ciscoProducts 483 }

-- Cisco Catalyst c2950 switch with 8 10BaseS VDSL Ports and 2 ST (SFP or 10/100/1000 Base T) (WS-C2950ST-8-LRE)

catalyst295024LREG  OBJECT IDENTIFIER
    ::= { ciscoProducts 484 }

-- Cisco Catalyst c2950 switch with 24 10BaseS VDSL Ports and 2 GBIC ( Gigabit Interface Converter ) slots (WS-C2950G-24-LRE)

catalyst355024PWR  OBJECT IDENTIFIER
    ::= { ciscoProducts 485 }

-- Catalyst 3550 24 10/100 ports with inline power and 2 Gig uplinks fixed configuration Layer 2/Layer 3 Ethernet Switch

ciscoCDM4630  OBJECT IDENTIFIER
    ::= { ciscoProducts 486 }

-- Cisco Content Distribution Manager Model 4630

ciscoCDM4650  OBJECT IDENTIFIER
    ::= { ciscoProducts 487 }

-- Cisco Content Distribution Manager Model 4650

catalyst2955T12  OBJECT IDENTIFIER
    ::= { ciscoProducts 488 }

-- Cisco Catalyst c2955 Industrial switch with 12 10/100 BaseTX ports and 2 10/100/1000 Base-TX ports

catalyst2955C12  OBJECT IDENTIFIER
    ::= { ciscoProducts 489 }

-- Cisco Catalyst c2955 Industrial switch with 12 10/100 Base TX ports and 2 100 Base-FX ports

ciscoCE508  OBJECT IDENTIFIER
    ::= { ciscoProducts 490 }

-- Cisco Content Engine Model 508

ciscoCE565  OBJECT IDENTIFIER
    ::= { ciscoProducts 491 }

-- Cisco Content Engine Model 565

ciscoCE7325  OBJECT IDENTIFIER
    ::= { ciscoProducts 492 }

-- Cisco Content Engine Model 7325

ciscoONS15454  OBJECT IDENTIFIER
    ::= { ciscoProducts 493 }

-- Cisco ONS 15454 Platform

ciscoONS15327  OBJECT IDENTIFIER
    ::= { ciscoProducts 494 }

-- Cisco ONS 15327 Platform

cisco837  OBJECT IDENTIFIER
    ::= { ciscoProducts 495 }

-- Cisco 837 platform with 4-port 10/100 Base-T Ethernet Switch,1 ADSL over POTS interface,data only model, hardware encryption

ciscoSOHO97  OBJECT IDENTIFIER
    ::= { ciscoProducts 496 }

-- SOHO (Small Office Home Office) Router with 4-port 10/100 Base-T Ethernet Switch,1 ADSL over POTS interface,data only model

cisco831  OBJECT IDENTIFIER
    ::= { ciscoProducts 497 }

-- Cisco 831 platform with 4-port 10/100 Base-T Ethernet Switch, 1 10Base-T Ethernet WAN interface, hardware encryption

ciscoSOHO91  OBJECT IDENTIFIER
    ::= { ciscoProducts 498 }

-- SOHO (Small Office Home Office)Router with 4-port 10/100 Base-T Ethernet Switch, 1 10Base-T Ethernet WAN interface

cisco836  OBJECT IDENTIFIER
    ::= { ciscoProducts 499 }

-- Cisco 836 platform with 4-port 10/100 Base-T Ethernet Switch, 1 ADSL over ISDN interface,1 ISDN BRI S/T interface, hardware encryption

ciscoSOHO96  OBJECT IDENTIFIER
    ::= { ciscoProducts 500 }

-- SOHO (Small Office Home Office)Router with 4-port 10/100 Base-T Ethernet Switch, 1 ADSL over ISDN interface, 1 ISDN BRI S/T interface

cat4507  OBJECT IDENTIFIER
    ::= { ciscoProducts 501 }

-- Catalyst 4000 with 7 slots (WS-C4507)

cat4506  OBJECT IDENTIFIER
    ::= { ciscoProducts 502 }

-- Catalyst 4000 with 6 slots (WS-C4506)

cat4503  OBJECT IDENTIFIER
    ::= { ciscoProducts 503 }

-- Catalyst 4000 with 3 slots (WS-C4503)

ciscoCE7305  OBJECT IDENTIFIER
    ::= { ciscoProducts 504 }

-- Cisco Content Engine Model 7305

ciscoCE510  OBJECT IDENTIFIER
    ::= { ciscoProducts 505 }

-- Cisco Content Engine Model 510

ciscoAIRAP1100  OBJECT IDENTIFIER
    ::= { ciscoProducts 507 }

-- 1100 series WLAN Access Point with 1 10/100TX port, 1 IEEE 802.11 radio port.

catalyst2955S12  OBJECT IDENTIFIER
    ::= { ciscoProducts 508 }

-- Cisco Catalyst c2955 Industrial switch with 12 10/100 Base T ports and 2 100 Base-LX Single Mode Uplink ports

cisco7609  OBJECT IDENTIFIER
    ::= { ciscoProducts 509 }

-- Cisco 7600 Series Chassis with 9 slots

ciscoWSC65509  OBJECT IDENTIFIER
    ::= { ciscoProducts 510 }


catalyst375024  OBJECT IDENTIFIER
    ::= { ciscoProducts 511 }

-- Catalyst 3750 24 10/100 ports + 2 Ethernet Gigabit SFP ports fixed configuration Layer 2/Layer 3 Ethernet  Stackable switch.

catalyst375048  OBJECT IDENTIFIER
    ::= { ciscoProducts 512 }

-- Catalyst 3750 48 10/100 ports + 4 Ethernet Gigabit SFP ports fixed configuration Layer 2/Layer 3 Ethernet  Stackable switch.

catalyst375024TS  OBJECT IDENTIFIER
    ::= { ciscoProducts 513 }

-- Catalyst 3750 24TS: 24 10/100/1000 ports + 4 Ethernet Gigabit SFP ports fixed configuration Layer 2/Layer 3 Ethernet  Stackable switch.

catalyst375024T  OBJECT IDENTIFIER
    ::= { ciscoProducts 514 }

-- Catalyst 3750 24T: 24 10/100/1000 ports fixed configuration Layer 2/Layer 3 Ethernet  Stackable switch.

catalyst37xxStack  OBJECT IDENTIFIER
    ::= { ciscoProducts 516 }

-- A stack of any catalyst37xx stack-able ethernet switches with unified identity (as a single unified switch), control and management.

ciscoGSS  OBJECT IDENTIFIER
    ::= { ciscoProducts 517 }

-- The Global Site Selector (GSS) is a network appliance that performs global server load balancing for geographically dispersed server load balancers and caches using DNS resolution.

ciscoPrimaryGSSM  OBJECT IDENTIFIER
    ::= { ciscoProducts 518 }

-- The Primary Global Site Selector Manager (GSSM) serves as the central management station for a Global Site Selector (GSS) Network.

ciscoStandbyGSSM  OBJECT IDENTIFIER
    ::= { ciscoProducts 519 }

-- The Standby Global Site Selector Manager (GSSM) serves as the backup to the Primary GSSM in a Global Site Selector(GSS) Network.

ciscoMWR1941DC  OBJECT IDENTIFIER
    ::= { ciscoProducts 520 }

-- The Mobile Wireless Router (MWR-1941-DC) is a router with a universal power supply targeted at application in a cell site Base Transceiver Station (BTS) providing T1/E1 backhaul connections to the aggregation node in Radio Access Networks (RAN)

ciscoDSC9216K9  OBJECT IDENTIFIER
    ::= { ciscoProducts 521 }

-- DS-C9216-K9    -  MDS 9216 16-port 2Gbps FC + 1-slot Modular Switch

cat6500FirewallSm  OBJECT IDENTIFIER
    ::= { ciscoProducts 522 }

-- High performance firewall blade for Catalyst 6500 Series

ciscoSCA11000  OBJECT IDENTIFIER
    ::= { ciscoProducts 523 }


ciscoCSM  OBJECT IDENTIFIER
    ::= { ciscoProducts 524 }

-- Cisco Content Switching Module (CSM) which load balancing internet traffic based on the layer 4 through layer 7 information in the content.

ciscoAIRAP1210  OBJECT IDENTIFIER
    ::= { ciscoProducts 525 }

-- 1200 series WLAN Access Point on Cisco IOS platform with 1 10/100TX port, 1 CardBus slot, 1 Mini PCI slot.

ciscoSCA211000  OBJECT IDENTIFIER
    ::= { ciscoProducts 526 }


catalyst297024  OBJECT IDENTIFIER
    ::= { ciscoProducts 527 }

-- Catalyst 2970 24: 24 10/100/1000 ports fixed configuration Layer 2 Ethernet  switch

cisco7613  OBJECT IDENTIFIER
    ::= { ciscoProducts 528 }

-- Cisco Internet router 7600 Series Chassis with 13 slots

ciscoSN54282  OBJECT IDENTIFIER
    ::= { ciscoProducts 529 }


catalyst3750Ge12Sfp  OBJECT IDENTIFIER
    ::= { ciscoProducts 530 }

-- Cisco Catalyst c3750 switch with 12 SFP (Small Form  FactorPluggable) Gigabit Ethernet ports

ciscoCR4430  OBJECT IDENTIFIER
    ::= { ciscoProducts 531 }

-- Cisco Content Router Model 4430

ciscoCR4450  OBJECT IDENTIFIER
    ::= { ciscoProducts 532 }

-- Cisco Content Router Model 4450

ciscoAIRBR1410  OBJECT IDENTIFIER
    ::= { ciscoProducts 533 }

-- 1410 Series Wireless LAN Bridge on Cisco IOS platform with 1 10/100Tx port and 1 5-GHz radio

ciscoWSC6509neba  OBJECT IDENTIFIER
    ::= { ciscoProducts 534 }

-- Catalyst 6500 series chassis with 9 slots

catalyst375048PS  OBJECT IDENTIFIER
    ::= { ciscoProducts 535 }

-- Catalyst 3750 48 10/100 In-Line Power Ethernet ports + 2 Gigabit Ethernet SFP ports fixed configuration Layer 2/Layer 3 Ethernet Stackable switch. (SFP Small Form factor Plugable)

catalyst375024PS  OBJECT IDENTIFIER
    ::= { ciscoProducts 536 }

-- Catalyst 3750 24 10/100 In-Line Power Ethernet ports + 4 Gigabit Ethernet SFP ports fixed configuration Layer 2/Layer 3 Ethernet Stackable switch. (SFP Small Form factor Plugable)

catalyst4510  OBJECT IDENTIFIER
    ::= { ciscoProducts 537 }

-- Catalyst 4000 with 10 slots (WS-C4510R)

cisco1711  OBJECT IDENTIFIER
    ::= { ciscoProducts 538 }

-- Enhanced security router with 4 FastEthernet switch ports, 1 Analog modem port, 1 FastEthernet port and a hardware encryption module

cisco1712  OBJECT IDENTIFIER
    ::= { ciscoProducts 539 }

-- Enhanced security router with 4 FastEthernet switch ports, 1 Basic Rate Interface(S/T)  data port, 1 FastEthernet port and a hardware encryption module.

catalyst29408TT  OBJECT IDENTIFIER
    ::= { ciscoProducts 540 }

-- Catalyst 2940 L2 switch with 8 10/100 copper ports and 1 10/100/1000 copper uplink port.

catalyst29408TF  OBJECT IDENTIFIER
    ::= { ciscoProducts 542 }

-- Catalyst 2940 L2 switch with 8 10/100 copper ports, 1 100 FX Uplink port and 1 Gigabit SFP Module slot.

cisco3825  OBJECT IDENTIFIER
    ::= { ciscoProducts 543 }

-- Two Network Module Slots, Four WIC slots, Two Gigabit Ethernet ports 3800 family router

cisco3845  OBJECT IDENTIFIER
    ::= { ciscoProducts 544 }

-- Four Network Module Slots, Four WIC slots, Two Gigabit Ethernet ports 3800 family router

cisco2430Iad24Fxs  OBJECT IDENTIFIER
    ::= { ciscoProducts 545 }

-- IAD2430 with 24FXS, 2FE

cisco2431Iad8Fxs  OBJECT IDENTIFIER
    ::= { ciscoProducts 546 }

-- IAD2431 with 8FXS, 2FE, 1T1/E1

cisco2431Iad16Fxs  OBJECT IDENTIFIER
    ::= { ciscoProducts 547 }

-- IAD2431 with 16FXS, 2FE, 1T1/E1

cisco2431Iad1T1E1  OBJECT IDENTIFIER
    ::= { ciscoProducts 548 }

-- IAD2431 with 2FE, 2T1/E1

cisco2432Iad24Fxs  OBJECT IDENTIFIER
    ::= { ciscoProducts 549 }

-- IAD2432 with 24FXS, 2FE, 2T1E1

cisco1701ADSLBRI  OBJECT IDENTIFIER
    ::= { ciscoProducts 550 }

-- Bacardi is a fixed configuration sku with ADSL WIC and ISDN BRI (S/T) or (S/T-V2) WIC

catalyst2950St24LRE997  OBJECT IDENTIFIER
    ::= { ciscoProducts 551 }

-- Catalyst2950 Long Reach Ethernet switch that confirms to ETSI 997 with 24 LRE interfaces, 2 10/100/1000 Small form factor copper interfaces and DC power supply(WS-C2950ST-24-LRE-997)

ciscoAirAp350IOS  OBJECT IDENTIFIER
    ::= { ciscoProducts 552 }

-- Cisco Wireless LAN Access Point 350 series on IOS platform with 1 10/100TX port, 1 IEEE 802.11 radio port

cisco3220  OBJECT IDENTIFIER
    ::= { ciscoProducts 553 }

-- 3220 - Mobile Access Router (MAR)

cat6500SslSm  OBJECT IDENTIFIER
    ::= { ciscoProducts 554 }

-- SSLSM is a High-Speed SSL Termination Engine for Catalyst 6000 family of platforms that terminates and accelarates Secure Socket Layer (SSL) transactions in Web server environement.

ciscoSIMSE  OBJECT IDENTIFIER
    ::= { ciscoProducts 555 }

-- ciscoSIMSE is an appliance - CiscoWorks Security Information Management Solution Engine

ciscoESSE  OBJECT IDENTIFIER
    ::= { ciscoProducts 556 }

-- Cisco Ethernet Subscriber Solution Engine

catalyst6kSup720  OBJECT IDENTIFIER
    ::= { ciscoProducts 557 }

-- Catalyst 6500 Supervisor Module 720 CPU board that is treated as a standalone system by the NMS

ciscoVG224  OBJECT IDENTIFIER
    ::= { ciscoProducts 558 }

-- Line side Analog Gateway with 24FXS Analog ports

catalyst295048T  OBJECT IDENTIFIER
    ::= { ciscoProducts 559 }

-- Cisco Catalyst c2950 switch with 48 10/100BaseT ports and 2 fixed 10/100/1000BaseT ports

catalyst295048SX  OBJECT IDENTIFIER
    ::= { ciscoProducts 560 }

-- Cisco Catalyst c2950 switch with 48 10/100BaseT ports and 2 fixed 1000Base Multimode fiber (SX) ports

catalyst297024TS  OBJECT IDENTIFIER
    ::= { ciscoProducts 561 }

-- Catalyst 2970 24TS: 24 10/100/1000 ports + 4 Ethernet Gigabit SFP ports fixed configuration Layer 2 Ethernet  switch

ciscoNmNam  OBJECT IDENTIFIER
    ::= { ciscoProducts 562 }

-- Cisco NM-NAM, NAM for the branch office routers

catalyst356024PS  OBJECT IDENTIFIER
    ::= { ciscoProducts 563 }

-- Catalyst 3750 24 10/100 ports with In-Line Power + 2 Gigabit SFP ports fixed configuration Layer 2/Layer 3 Ethernet Switch.(SFP Small Formfactor Pluggable)

catalyst356048PS  OBJECT IDENTIFIER
    ::= { ciscoProducts 564 }

-- Catalyst 3750 48 10/100 ports with In-Line Power + 4 Gigabit SFP ports fixed configuration Layer 2/Layer 3 Ethernet Switch.(SFP Small Formfactor Pluggable)

ciscoAIRBR1300  OBJECT IDENTIFIER
    ::= { ciscoProducts 565 }

-- Cisco Aironet 1300 Series Wireless Bridge with 1 10/100TX Ethernet port, 1 IEEE 802.11g radio port

cisco851  OBJECT IDENTIFIER
    ::= { ciscoProducts 566 }

-- Cisco 851 platform with 1 10/100T ethernet WAN interface, 4-port 10/100 Base-T LAN Ethernet switch, 4 USB ports, hardware encryption and Wireless LAN card

cisco857  OBJECT IDENTIFIER
    ::= { ciscoProducts 567 }

-- Cisco 857 platform with 1 DSL over POTS WAN interface, 4-port 10/100 Base-T LAN Ethernet switch, 4 USB ports, hardware encryption and an optional Wireless LAN card

cisco876  OBJECT IDENTIFIER
    ::= { ciscoProducts 568 }

-- Cisco 876 platform with 1 ADSL over ISDN WAN interface, 4-port 10/100 Base-T LAN Ethernet switch, 4 USB ports, 1 ISDN BRI S/T interface, hardware encryption and an optional Wireless LAN card

cisco877  OBJECT IDENTIFIER
    ::= { ciscoProducts 569 }

-- Cisco 877 platform with 1 ADSL over POTS WAN interface, 4-port 10/100 BASE-T LAN Ethernet switch, 4 USB ports, hardware encryption and an optional Wireless LAN card

cisco878  OBJECT IDENTIFIER
    ::= { ciscoProducts 570 }

-- Cisco 878 platform with 1 SHDSL WAN interface, 4-port 1 0/100 Base-T LAN Ethernet switch, 4 USB ports, 1 ISDN BRI S/T interface, hardware encryption and an optional Wireless LAN card.

cisco871  OBJECT IDENTIFIER
    ::= { ciscoProducts 571 }

-- Cisco 871 platform with 1 10/100T ethernet WAN interface, 4-port 10/100 Base-T LAN Ethernet switch, 4 USB ports, hardware encryption and an optional Wireless LAN card

uMG9820  OBJECT IDENTIFIER
    ::= { ciscoProducts 572 }


catalyst6kGateway  OBJECT IDENTIFIER
    ::= { ciscoProducts 573 }

-- Catalyst 6000 Acess Gateway line card supporting voice and WAN(Wide Area Network) interfaces as well as conferencing and transcoding services

catalyst375024ME  OBJECT IDENTIFIER
    ::= { ciscoProducts 574 }

-- Metro Ethernet Catalyst 3750   24-10/100 + 2 SFP (Small Formfactor Pluggable) ports for downlinks and 2 SFP ES(Enhanched Service) ports for uplinks

catalyst4000NAM  OBJECT IDENTIFIER
    ::= { ciscoProducts 575 }

-- Network analysis Module (NAM) for Catalyst 4000

cisco2811  OBJECT IDENTIFIER
    ::= { ciscoProducts 576 }

-- Cisco 2800 series router with one Network Module slot, four HWIC slots, two fast etherenet and integrated VPN

cisco2821  OBJECT IDENTIFIER
    ::= { ciscoProducts 577 }

-- Cisco 2800 series router with one Network Module slot, one EVM, four HWIC slots, two gigabit ethernet and intergrated VPN

cisco2851  OBJECT IDENTIFIER
    ::= { ciscoProducts 578 }

-- Cisco 2800 series router with one double wide Network Module slot, one EVM, four HWIC slots, two gigabit ethernet and integrated VPN

cisco3201WMIC  OBJECT IDENTIFIER
    ::= { ciscoProducts 581 }


ciscoMCS7815I  OBJECT IDENTIFIER
    ::= { ciscoProducts 582 }

-- Cisco Media Convergence Server 7815 (IBM)

ciscoMCS7825H  OBJECT IDENTIFIER
    ::= { ciscoProducts 583 }

-- Cisco Media Convergence Server 7825 (HP)

ciscoMCS7835H  OBJECT IDENTIFIER
    ::= { ciscoProducts 584 }

-- Cisco Media Convergence Server 7835 (HP)

ciscoMCS7835I  OBJECT IDENTIFIER
    ::= { ciscoProducts 585 }

-- Cisco Media Convergence Server 7835 (IBM)

ciscoMCS7845H  OBJECT IDENTIFIER
    ::= { ciscoProducts 586 }

-- Cisco Media Convergence Server 7845 (HP)

ciscoMCS7845I  OBJECT IDENTIFIER
    ::= { ciscoProducts 587 }

-- Cisco Media Convergence Server 7845 (IBM)

ciscoMCS7855I  OBJECT IDENTIFIER
    ::= { ciscoProducts 588 }

-- Cisco Media Convergence Server 7855 (IBM)

ciscoMCS7865I  OBJECT IDENTIFIER
    ::= { ciscoProducts 589 }

-- Cisco Media Convergence Server 7865 (IBM)

cisco12006  OBJECT IDENTIFIER
    ::= { ciscoProducts 590 }

-- Cisco 12000 platform with 6 slots

catalyst3750G16TD  OBJECT IDENTIFIER
    ::= { ciscoProducts 591 }

-- Cisco Catalyst 3750 switch with 16 gigabit and one 10G ethernet port (WS-C3750G-16TD)

ciscoIGESM  OBJECT IDENTIFIER
    ::= { ciscoProducts 592 }

-- Cisco Systems Intelligent Gigabit Ethernet Switch Module for IBM eServer BladeCenter (OS-CIGESM-18TT-E)

ciscoCCM  OBJECT IDENTIFIER
    ::= { ciscoProducts 593 }

cisco1718  OBJECT IDENTIFIER
    ::= { ciscoProducts 594 }


ciscoCe511K9  OBJECT IDENTIFIER
    ::= { ciscoProducts 595 }

-- Cisco Content Engine Model CE-511-K9

ciscoCe566K9  OBJECT IDENTIFIER
    ::= { ciscoProducts 596 }

-- Cisco Content Engine Model CE-566-K9

ciscoMGX8830Pxm45  OBJECT IDENTIFIER
    ::= { ciscoProducts 597 }


ciscoMGX8880  OBJECT IDENTIFIER
    ::= { ciscoProducts 598 }

-- Cisco MGX8880 switch with 32 half height slots

ciscoWsSvcWLAN1K9  OBJECT IDENTIFIER
    ::= { ciscoProducts 599 }

-- Wireless LAN Module (WS-SVC-WLAN-1-K9) is a Komodo+ based line card for Cat6K family of platforms, which provides wireless domain services (WDS) for IEEE 802.11 wireless clients

ciscoCe7306K9  OBJECT IDENTIFIER
    ::= { ciscoProducts 600 }

-- Cisco Content Engine Model CE-7306-K9

ciscoCe7326K9  OBJECT IDENTIFIER
    ::= { ciscoProducts 601 }

-- Cisco Content Engine Model CE-7326-K9

catalyst3750G24PS  OBJECT IDENTIFIER
    ::= { ciscoProducts 602 }

-- Catalyst 3750 24 10/100/1000 Power over Ethernet ports + 4 Gigabit Ethernet SFP ports fixed configuration Layer 2/Layer 3 Ethernet Stackable switch. (SFP Small Form factor Pluggable)

catalyst3750G48PS  OBJECT IDENTIFIER
    ::= { ciscoProducts 603 }

-- Catalyst 3750 48 10/100/1000 Power over Ethernet ports + 4 Gigabit Ethernet SFP ports fixed configuration Layer2/Layer 3 Ethernet Stackable switch. (SFP Small Form factor Pluggable)

catalyst3750G48TS  OBJECT IDENTIFIER
    ::= { ciscoProducts 604 }

-- Catalyst 3750 48 10/100/1000 ports + 4 Gigabit Ethernet SFP ports fixed configuration Layer 2/Layer 3 Ethernet Stackable switch. (SFP Small Form factor Pluggable)

ciscoBMGX8830Pxm45  OBJECT IDENTIFIER
    ::= { ciscoProducts 606 }

-- PXM45 based Multiservice Switch (Model B) with 14 half height slots

ciscoBMGX8830Pxm1E  OBJECT IDENTIFIER
    ::= { ciscoProducts 607 }

-- PXM1E based Multiservice Switch (Model B) with 14 half height slots

ciscoBMGX8850Pxm45  OBJECT IDENTIFIER
    ::= { ciscoProducts 608 }

-- PXM45 based Multiservice Gigabit Switch (ModelB) with 32 half height slots

ciscoBMGX8850Pxm1E  OBJECT IDENTIFIER
    ::= { ciscoProducts 609 }

-- PXM1E based Multiservice Gigabit Switch (ModelB) with 32 half height slots

ciscoSSLCSM  OBJECT IDENTIFIER
    ::= { ciscoProducts 610 }


ciscoNetworkRegistrar  OBJECT IDENTIFIER
    ::= { ciscoProducts 611 }

-- Cisco Network Registrar (CNR) is a full-featured DNS/DHCP system that provides scalable naming and addressing services for enterprise and service provider networks.

ciscoCe501K9  OBJECT IDENTIFIER
    ::= { ciscoProducts 612 }

-- Cisco Content Engine Model CE-501-K9

ciscoCRS16S  OBJECT IDENTIFIER
    ::= { ciscoProducts 613 }

-- Cisco CRS-1 Series Single Chassis Carrier Routing System

catalyst3560G24PS  OBJECT IDENTIFIER
    ::= { ciscoProducts 614 }

-- Catalyst 3560 24 10/100/1000 Power over Ethernet ports + 4 Gigabit Ethernet SFP ports fixed configuration Layer 2/Layer 3 Ethernet switch. (SFP Small Form factor Pluggable)

catalyst3560G24TS  OBJECT IDENTIFIER
    ::= { ciscoProducts 615 }

-- Catalyst 3560 24 10/100/1000 Ethernet ports + 4 Gigabit Ethernet SFP ports fixed configuration Layer 2/Layer 3 Ethernet switch (SFP Small Form factor Pluggable)

catalyst3560G48PS  OBJECT IDENTIFIER
    ::= { ciscoProducts 616 }

-- Catalyst 3560 48 10/100/1000 Power over Ethernet ports + 4 Gigabit Ethernet SFP ports fixed configuration Layer 2/Layer 3 Ethernet switch. (SFP Small Form factor Pluggable)

catalyst3560G48TS  OBJECT IDENTIFIER
    ::= { ciscoProducts 617 }

-- Catalyst 3560 48 10/100/1000 ports + 4 Gigabit Ethernet SFP ports fixed configuration Layer 2/Layer 3 Ethernet switch. (SFP Small Form factor Pluggable)

ciscoAIRAP1130  OBJECT IDENTIFIER
    ::= { ciscoProducts 618 }

-- Cisco Aironet 1130 series WLAN Access Point with 1 10/100TX port, dual IEEE 802.11a and 802.11g  radio port

cisco2801  OBJECT IDENTIFIER
    ::= { ciscoProducts 619 }

-- 1700 Next Generation voice enabled router with 4 slots

cisco1841  OBJECT IDENTIFIER
    ::= { ciscoProducts 620 }

-- 1700 Next Generation data only router with 2 slots

ciscoWsSvcMWAM1  OBJECT IDENTIFIER
    ::= { ciscoProducts 621 }

-- Multiprocessor WAN Application Module (WS-SVC-MWAM-1) is a multipurpose blade built for the Cat6k platform

ciscoNMCUE  OBJECT IDENTIFIER
    ::= { ciscoProducts 622 }

-- Cisco Unity Express network module (NM-CUE)

ciscoAIMCUE  OBJECT IDENTIFIER
    ::= { ciscoProducts 623 }

-- Cisco Unity Express advanced integration module (AIM-CUE)

catalyst3750G24TS1U  OBJECT IDENTIFIER
    ::= { ciscoProducts 624 }

-- Catalyst 3750 24 10/100/1000 Ethernet ports + 4 Gigabit Ethernet SFP ports fixed configuration Layer 2/Layer 3 Ethernet Stackable switch. (SFP Small Form factor Pluggable)

cisco371098HP001  OBJECT IDENTIFIER
    ::= { ciscoProducts 625 }

-- 24 port Gigabit Ethernet switch module for HP ProLiant BL p-class server chassis

catalyst4948  OBJECT IDENTIFIER
    ::= { ciscoProducts 626 }

-- Fixed configuration Catalyst 4000 with 48 10/100/1000BaseT ports and 4 1000BaseX SFP ports (WS-C4948)

ciscoSB101  OBJECT IDENTIFIER
    ::= { ciscoProducts 627 }


ciscoSB106  OBJECT IDENTIFIER
    ::= { ciscoProducts 628 }


ciscoSB107  OBJECT IDENTIFIER
    ::= { ciscoProducts 629 }


ciscoWLSE1130  OBJECT IDENTIFIER
    ::= { ciscoProducts 630 }

-- Cisco WLAN Solution Engine (WLSE) 1130 monitors and configures a WLAN with Cisco WAP and Bridges

ciscoWLSE1030  OBJECT IDENTIFIER
    ::= { ciscoProducts 631 }

-- Cisco WLSE Express 1030 is a  WLSE that monitors and configures a WLAN with Cisco WAP and Bridges with AAA functionality

ciscoHSE1140  OBJECT IDENTIFIER
    ::= { ciscoProducts 632 }

-- Cisco Hosting Solution Engine 1140 manages Cisco powered data centers and Points of Presence with routers, switches, server load balancers, firewalls, intrusion detection systems and other layer 4-7 content delivery products

catalyst356024TS  OBJECT IDENTIFIER
    ::= { ciscoProducts 633 }

-- Catalyst 3560 24 10/100 ports + 2 Ethernet Gigabit SFP ports fixed configuration Layer 2/Layer 3 Ethernet switch.

catalyst356048TS  OBJECT IDENTIFIER
    ::= { ciscoProducts 634 }

-- Catalyst 3560 48 10/100 ports + 4 Ethernet Gigabit SFP ports fixed configuration Layer 2/Layer 3 Ethernet switch

ciscoWsSvcadsm1K9  OBJECT IDENTIFIER
    ::= { ciscoProducts 635 }


ciscoWsSvcagsm1K9  OBJECT IDENTIFIER
    ::= { ciscoProducts 636 }


ciscoONS15310  OBJECT IDENTIFIER
    ::= { ciscoProducts 637 }


cisco1801  OBJECT IDENTIFIER
    ::= { ciscoProducts 638 }

-- Cisco 1800 platform with 1 ADSL over POTS WAN interface, 1 ISDNBRI S/T interface, 8-port 10/100 Base-T LAN Ethernet switch, 2 USB ports and an optional Wireless LAN card.

cisco1802  OBJECT IDENTIFIER
    ::= { ciscoProducts 639 }

-- Cisco 1800 platform with 1 ADSL over ISDN WAN interface, 1 ISDN BRI S/T interface, 8-port 10/100 Base-T LAN Ethernet switch, 2 USB ports and an optional Wireless LAN card.

cisco1803  OBJECT IDENTIFIER
    ::= { ciscoProducts 640 }

-- Cisco 1800 platform with 1 G.SHDSL 4-wire interface, 1 ISDN BRI S/T interface, 8-port 10/100 Base-T LAN Ethernet switch, 2 USB ports and an optional Wireless LAN card.

cisco1811  OBJECT IDENTIFIER
    ::= { ciscoProducts 641 }

-- Cisco 1800 platform with V.92 Modem, 8-port 10/100 Base-T LAN Ethernet switch, 2 USB ports and an optional Wireless LAN card.

cisco1812  OBJECT IDENTIFIER
    ::= { ciscoProducts 642 }

-- Cisco 1800 platform with ISDN BRI S/T interface, 8-port 10/100 Base-T LAN Ethernet switch, 2 USB ports and an optional Wireless LAN card.

ciscoCRS8S  OBJECT IDENTIFIER
    ::= { ciscoProducts 643 }

-- Cisco CRS-1 Series 8 Slots Carrier Routing System

ciscoIDS4210  OBJECT IDENTIFIER
    ::= { ciscoProducts 645 }

-- Cisco Intrusion Detection System 4210

ciscoIDS4215  OBJECT IDENTIFIER
    ::= { ciscoProducts 646 }

-- Cisco Intrusion Detection System 4215

ciscoIDS4235  OBJECT IDENTIFIER
    ::= { ciscoProducts 647 }

-- Cisco Intrusion Detection System 4235

ciscoIPS4240  OBJECT IDENTIFIER
    ::= { ciscoProducts 648 }

-- Cisco Intrusion Prevention System 4240

ciscoIDS4250  OBJECT IDENTIFIER
    ::= { ciscoProducts 649 }

-- Cisco Intrusion Detection System 4250

ciscoIDS4250SX  OBJECT IDENTIFIER
    ::= { ciscoProducts 650 }

-- Cisco Intrusion Detection System 4250 SX

ciscoIDS4250XL  OBJECT IDENTIFIER
    ::= { ciscoProducts 651 }

-- Cisco Intrusion Detection System 4250 XL

ciscoIPS4255  OBJECT IDENTIFIER
    ::= { ciscoProducts 652 }

-- Cisco Intrusion Prevention System 4255

ciscoIDSIDSM2  OBJECT IDENTIFIER
    ::= { ciscoProducts 653 }

-- Cisco Intrusion Detection System Module IDSM2

ciscoIDSNMCIDS  OBJECT IDENTIFIER
    ::= { ciscoProducts 654 }

-- Cisco Intrusion Detection System Network Module NM-CIDS

ciscoIPSSSM20  OBJECT IDENTIFIER
    ::= { ciscoProducts 655 }

-- Cisco Intrusion Prevention System Security Service Module SSM-20

catalyst375024FS  OBJECT IDENTIFIER
    ::= { ciscoProducts 656 }

-- Catalyst 3750 24 100BaseFX ports + 2 Ethernet Gigabit SFP ports fixed configuration Layer 2/Layer 3 Ethernet switch.

ciscoWSC6504E  OBJECT IDENTIFIER
    ::= { ciscoProducts 657 }

-- Catalyst 6000 series chassis with 4 slots

cisco7604  OBJECT IDENTIFIER
    ::= { ciscoProducts 658 }

-- Cisco Optical Services Router 7600 Series Chassis with 4 slots

catalyst494810GE  OBJECT IDENTIFIER
    ::= { ciscoProducts 659 }

-- Catalyst 4000 series fixed configuration switch with 48 10/100/1000BaseT wirespeed ports and two 10Gbps ports

ciscoIGESMSFP  OBJECT IDENTIFIER
    ::= { ciscoProducts 660 }

-- Cisco Systems Intelligent Gigabit Ethernet Switch Module with external SFPs for IBM eServer BladeCenter (OS-CIGESM-18-SFP-E)

ciscoFE6326K9  OBJECT IDENTIFIER
    ::= { ciscoProducts 661 }

-- Cisco File Engine Model FE-6326-K9

ciscoIPSSSM10  OBJECT IDENTIFIER
    ::= { ciscoProducts 662 }

-- Cisco Intrusion Prevention System Security Service Module SSM-10

ciscoNme16Es1Ge  OBJECT IDENTIFIER
    ::= { ciscoProducts 663 }

-- EtherSwitch Service Module 16 10/100 ports + 1 Ethernet Gigabit port fixed configuration Layer 2/Layer 3 Ethernet switch.

ciscoNmeX24Es1Ge  OBJECT IDENTIFIER
    ::= { ciscoProducts 664 }

-- EtherSwitch Service Module 23 10/100 ports + 1 Ethernet Gigabit port fixed configuration Layer 2/Layer 3 Ethernet switch.

ciscoNmeXd24Es2St  OBJECT IDENTIFIER
    ::= { ciscoProducts 665 }

-- EtherSwitch Service Module 24 10/100 ports + 1 Ethernet Gigabit SFP port fixed configuration Layer 2/Layer 3 Ethernet Stackable switch.

ciscoNmeXd48Es2Ge  OBJECT IDENTIFIER
    ::= { ciscoProducts 666 }

-- EtherSwitch Service Module 48 10/100 ports + 2 Ethernet Gigabit SFP ports fixed configuration Layer 2/Layer 3 Ethernet switch.

cisco3202WMIC  OBJECT IDENTIFIER
    ::= { ciscoProducts 667 }


ciscoAs5400XM  OBJECT IDENTIFIER
    ::= { ciscoProducts 668 }

-- Cisco AS5400XM platform

ciscoASA5510  OBJECT IDENTIFIER
    ::= { ciscoProducts 669 }

-- Cisco Adaptive Security Appliance 5510

ciscoASA5520  OBJECT IDENTIFIER
    ::= { ciscoProducts 670 }

-- Cisco Adaptive Security Appliance 5520

ciscoASA5520sc  OBJECT IDENTIFIER
    ::= { ciscoProducts 671 }

-- Cisco Adaptive Security Appliance 5520 Security Context

ciscoASA5540  OBJECT IDENTIFIER
    ::= { ciscoProducts 672 }

-- Cisco Adaptive Security Appliance 5540

ciscoASA5540sc  OBJECT IDENTIFIER
    ::= { ciscoProducts 673 }

-- Cisco Adaptive Security Appliance 5540 Security Context

ciscoWsSvcFwm1sc  OBJECT IDENTIFIER
    ::= { ciscoProducts 674 }

-- Firewall Services Module for Catalyst 6500 Series Security Context

ciscoPIXFirewall535sc  OBJECT IDENTIFIER
    ::= { ciscoProducts 675 }

-- Cisco PIX Firewall 535 Security Context

ciscoPIXFirewall525sc  OBJECT IDENTIFIER
    ::= { ciscoProducts 676 }

-- Cisco PIX Firewall 525 Security Context

ciscoPIXFirewall515Esc  OBJECT IDENTIFIER
    ::= { ciscoProducts 677 }

-- Cisco PIX Firewall 515E Security Context

ciscoPIXFirewall515sc  OBJECT IDENTIFIER
    ::= { ciscoProducts 678 }

-- Cisco PIX Firewall 515 Security Context

ciscoAs5350XM  OBJECT IDENTIFIER
    ::= { ciscoProducts 679 }

-- Low end AS5350XM platfrom

ciscoFe7326K9  OBJECT IDENTIFIER
    ::= { ciscoProducts 680 }

-- Cisco File Engine Model FE-7326-K9

ciscoFe511K9  OBJECT IDENTIFIER
    ::= { ciscoProducts 681 }

-- Cisco File Engine Model FE-511-K9

ciscoSCEDispatcher  OBJECT IDENTIFIER
    ::= { ciscoProducts 682 }

-- Cisco Service Control Engine Dispatcher

ciscoSCE1000  OBJECT IDENTIFIER
    ::= { ciscoProducts 683 }

-- Cisco SCE1000 Service Control Engine

ciscoSCE2000  OBJECT IDENTIFIER
    ::= { ciscoProducts 684 }

-- Cisco SCE2000 Service Control Engine

ciscoAIRAP1240  OBJECT IDENTIFIER
    ::= { ciscoProducts 685 }

-- Cisco Aironet 1240 series WLAN Access Point with 1 10/100TX port, dual IEEE 802.11a and 802.11g radio ports, external antenna connectors

ciscoDSC9120CLK9  OBJECT IDENTIFIER
    ::= { ciscoProducts 686 }

-- DS-C9120-CL-K9  - MDS 9120-CL, 20-Port 4 Gbps Fibre Channel Fabric Switch, Commercial

ciscoFe611K9  OBJECT IDENTIFIER
    ::= { ciscoProducts 687 }

-- Cisco File Engine Model FE-611-K9

catalyst3750Ge12SfpDc  OBJECT IDENTIFIER
    ::= { ciscoProducts 688 }

-- Cisco Catalyst c3750 switch with 12 SFP (Small Form Factor Plugable) Gigabit Ethernet ports and DC power supply

cisco3271  OBJECT IDENTIFIER
    ::= { ciscoProducts 689 }


cisco3272  OBJECT IDENTIFIER
    ::= { ciscoProducts 690 }


cisco3241  OBJECT IDENTIFIER
    ::= { ciscoProducts 691 }


cisco3242  OBJECT IDENTIFIER
    ::= { ciscoProducts 692 }


ciscoICM  OBJECT IDENTIFIER
    ::= { ciscoProducts 693 }

-- Cisco Systems Intelligent Contact Management

catalyst296024  OBJECT IDENTIFIER
    ::= { ciscoProducts 694 }

-- Catalyst 2960 24 10/100 ports + 2 dual purpose Gigabit Ethernet ports fixed configuration Layer 2 Ethernet switch

catalyst296048  OBJECT IDENTIFIER
    ::= { ciscoProducts 695 }

-- Catalyst 2960 48 10/100 ports + 2 dual purpose Gigabit Ethernet ports fixed configuration Layer 2 Ethernet Switch

catalyst2960G24  OBJECT IDENTIFIER
    ::= { ciscoProducts 696 }

-- Catalyst 2960 20 10/100/1000 ports + 4 dual purpose Gigabit Ethernet ports fixed configuration Layer 2 Ethernet switch.

catalyst2960G48  OBJECT IDENTIFIER
    ::= { ciscoProducts 697 }

-- Catalyst 2960 44 10/100/1000 ports + 4 dual purpose Gigabit Ethernet ports fixed configuration Layer 2 Ethernet switch.

catalyst45503  OBJECT IDENTIFIER
    ::= { ciscoProducts 698 }


catalyst45506  OBJECT IDENTIFIER
    ::= { ciscoProducts 699 }


catalyst45507  OBJECT IDENTIFIER
    ::= { ciscoProducts 700 }


catalyst455010  OBJECT IDENTIFIER
    ::= { ciscoProducts 701 }


ciscoNme16Es1GeNoPwr  OBJECT IDENTIFIER
    ::= { ciscoProducts 702 }

-- EtherSwitch Service Module 16 10/100 ports + 1 Ethernet Gigabit port fixed configuration Layer 2/Layer 3 Ethernet switch with no inline power

ciscoNmeX24Es1GeNoPwr  OBJECT IDENTIFIER
    ::= { ciscoProducts 703 }

-- EtherSwitch Service Module 23 10/100 ports + 1 Ethernet Gigabit port fixed configuration Layer 2/Layer 3 Ethernet switch with no inline power

ciscoNmeXd24Es2StNoPwr  OBJECT IDENTIFIER
    ::= { ciscoProducts 704 }

-- EtherSwitch Service Module 24 10/100 ports + 1 Ethernet Gigabit SFP port fixed configuration Layer 2/Layer 3 Ethernet Stackable switch with no inline power

ciscoNmeXd48Es2GeNoPwr  OBJECT IDENTIFIER
    ::= { ciscoProducts 705 }

-- EtherSwitch Service Module 48 10/100 ports + 2 Ethernet Gigabit SFP ports fixed configuration Layer 2/Layer 3 Ethernet switch with no inline power

catalyst6kMsfc2a  OBJECT IDENTIFIER
    ::= { ciscoProducts 706 }

-- Multilevel Switching Feature Card Version 2a for Catalyst 6000 that is treated as a standalone system by the NMS

ciscoEDI  OBJECT IDENTIFIER
    ::= { ciscoProducts 707 }

-- Cisco Enhanced Device Interface Server

ciscoCe611K9  OBJECT IDENTIFIER
    ::= { ciscoProducts 708 }

-- Cisco Content Engine Model CE-611-K9

ciscoWLSEs20  OBJECT IDENTIFIER
    ::= { ciscoProducts 709 }

-- Cisco Wireless LAN Solution Engine S20.

ciscoMPX  OBJECT IDENTIFIER
    ::= { ciscoProducts 710 }

-- Cisco MeetingPlace Express

ciscoNMCUEEC  OBJECT IDENTIFIER
    ::= { ciscoProducts 711 }

-- Cisco Unity Express network module with enhanced capacity (NM-CUE-EC)

ciscoWLSE1132  OBJECT IDENTIFIER
    ::= { ciscoProducts 712 }

-- Cisco Wireless LAN Solution Engine WLSE-1132-K9

ciscoME6340ACA  OBJECT IDENTIFIER
    ::= { ciscoProducts 713 }

-- DSL Switch 48 port ADSL2/2+, Annex A, AC

ciscoME6340DCA  OBJECT IDENTIFIER
    ::= { ciscoProducts 714 }

-- DSL Switch 48 port ADSL2/2+, Annex A, DC

ciscoME6340DCB  OBJECT IDENTIFIER
    ::= { ciscoProducts 715 }

-- DSL Switch 48 port ADSL2/2+, Annex B, DC

catalyst296024TT  OBJECT IDENTIFIER
    ::= { ciscoProducts 716 }

-- Catalyst 2960 24 10/100 ports + 2 10/100/1000 ports fixed configuration Layer 2 Ethernet switch

catalyst296048TT  OBJECT IDENTIFIER
    ::= { ciscoProducts 717 }

-- Catalyst 2960 48 10/100 ports + 2 10/100/1000 ports fixed configuration Layer 2 Ethernet switch

ciscoIGESMSFPT  OBJECT IDENTIFIER
    ::= { ciscoProducts 718 }

-- Cisco Systems Intelligent Gigabit Ethernet Switch Module for IBM eServer BladeCenter Telco Chassis (OS-CIGESM-18TT-E)

ciscoMEC6524gs8s  OBJECT IDENTIFIER
    ::= { ciscoProducts 719 }

-- Cisco ME 6524 chassis with 24 port SFP and 8 SFP uplinks

ciscoMEC6524gt8s  OBJECT IDENTIFIER
    ::= { ciscoProducts 720 }

-- Cisco ME 6524 chassis with 24 port 10/100/1000BaseT and 8 SFP uplinks

ciscoMEC6724s10x2  OBJECT IDENTIFIER
    ::= { ciscoProducts 721 }


ciscoMEC6724t10x2  OBJECT IDENTIFIER
    ::= { ciscoProducts 722 }


ciscoPaldron  OBJECT IDENTIFIER
    ::= { ciscoProducts 723 }

-- ARM Development Platform

catalystsExpress50024TT  OBJECT IDENTIFIER
    ::= { ciscoProducts 724 }

-- Catalyst Express 500 24 10/100 ports + 2 Gigabit Ethernet ports fixed configuration Layer 2 Ethernet switch

catalystsExpress50024LC  OBJECT IDENTIFIER
    ::= { ciscoProducts 725 }

-- Catalyst Express 500 24 10/100 ports (4 Power Over Ethernet Ports) + 2 dual purpose Gigabit Ethernet ports fixed configuration Layer 2 Ethernet switch

catalystsExpress50024PC  OBJECT IDENTIFIER
    ::= { ciscoProducts 726 }

-- Catalyst Express 500 24  Power Over Ethernet Ports + 2 dual purpose Gigabit Ethernet ports fixed configuration Layer 2 Ethernet switch

catalystsExpress50012TC  OBJECT IDENTIFIER
    ::= { ciscoProducts 727 }

-- Catalyst Express 500 8 Gigabit Ethernet Ports + 4 dual purpose Gigabit Ethernet ports fixed configuration Layer 2 Ethernet switch

ciscoIGESMT  OBJECT IDENTIFIER
    ::= { ciscoProducts 728 }

-- Cisco Systems Intelligent Gigabit Ethernet Switch Module for IBM eServer BladeCenter Telco Chassis (OS-CIGESM-18TT-E)

ciscoACE04G  OBJECT IDENTIFIER
    ::= { ciscoProducts 729 }


ciscoACE10K9  OBJECT IDENTIFIER
    ::= { ciscoProducts 730 }

-- Application Control Engine Module in Cat6500

cisco5750  OBJECT IDENTIFIER
    ::= { ciscoProducts 731 }

-- High Assurance Router

ciscoMWR1941DCA  OBJECT IDENTIFIER
    ::= { ciscoProducts 732 }

-- The Mobile Wireless Router (MWR-1941-DC-A) is a router with a universal power supply targeted at application in a cell site Base Transceiver Station (BTS) providing backhaul connections to the aggregation node in Radio Access Networks (RAN) and support for AIM module

cisco815  OBJECT IDENTIFIER
    ::= { ciscoProducts 733 }

-- Cisco 815 platform fixed configuration cable modem router with 4 FastEthernet switch ports, 1 Cable modem port, 1 FastEthernet port

cisco240024TSA  OBJECT IDENTIFIER
    ::= { ciscoProducts 734 }

-- Metro Ethernet 2400, 24 10/100 Fast Ethernet + 2 SFP ports fixed configuration Layer 2 Ethernet switch, AC power.

cisco240024TSD  OBJECT IDENTIFIER
    ::= { ciscoProducts 735 }

-- Metro Ethernet 2400, 24 10/100 Fast Ethernet + 2 SFP ports fixed configuration Layer 2 Ethernet switch, DC power.

cisco340024TSA  OBJECT IDENTIFIER
    ::= { ciscoProducts 736 }

-- Metro Ethernet 3400, 24 10/100 Fast Ethernet + 2 SFP ports fixed configuration Layer 2/3 Ethernet switch, AC power.

cisco340024TSD  OBJECT IDENTIFIER
    ::= { ciscoProducts 737 }

-- Metro Ethernet 3400, 24 10/100 Fast Ethernet + 2 SFP ports fixed configuration Layer 2/3 Ethernet switch, DC power.

ciscoCrs18Linecard  OBJECT IDENTIFIER
    ::= { ciscoProducts 738 }

-- Cisco CRS-1 Series 8 slot Line Card Chassis

ciscoCrs1Fabric  OBJECT IDENTIFIER
    ::= { ciscoProducts 739 }

-- Cisco CRS-1 Series Fabric Card Chassis

ciscoFE2636  OBJECT IDENTIFIER
    ::= { ciscoProducts 740 }

-- Cisco File Engine Module for 26xx and 36xx series platforms

ciscoIDS4220  OBJECT IDENTIFIER
    ::= { ciscoProducts 741 }

-- Cisco Intrusion Detection System 4220

ciscoIDS4230  OBJECT IDENTIFIER
    ::= { ciscoProducts 742 }

-- Cisco Intrusion Detection System 4230

ciscoIPS4260  OBJECT IDENTIFIER
    ::= { ciscoProducts 743 }

-- Cisco Intrusion Prevention System 4260

ciscoWsSvcSAMIBB  OBJECT IDENTIFIER
    ::= { ciscoProducts 744 }

-- Service and Application Module for IP

ciscoASA5505  OBJECT IDENTIFIER
    ::= { ciscoProducts 745 }

-- Cisco Adaptive Security Appliance 5505

ciscoMCS7825I  OBJECT IDENTIFIER
    ::= { ciscoProducts 746 }

-- Cisco Media Convergence Server 7825 (IBM)

ciscoWsC3750g24ps  OBJECT IDENTIFIER
    ::= { ciscoProducts 747 }

-- Cisco 3750 24+2 port 10/100/1000 Switch with integrated Cisco 4402 Wireless Controller

ciscoWs3020Hpq  OBJECT IDENTIFIER
    ::= { ciscoProducts 748 }

-- Cisco Catalyst Bladeswitch 3020 for HP

ciscoWs3030Del  OBJECT IDENTIFIER
    ::= { ciscoProducts 749 }

-- Cisco Catalyst Bladeswitch 3030 for Dell

ciscoSpaOc48posSfp  OBJECT IDENTIFIER
    ::= { ciscoProducts 750 }

-- 1-port OC48/STM16 POS/RPR SFP Optics Shared Port Adapter

catalyst6kEnhancedGateway  OBJECT IDENTIFIER
    ::= { ciscoProducts 751 }


ciscoWLSE1133  OBJECT IDENTIFIER
    ::= { ciscoProducts 752 }

-- Cisco Wireless LAN Solution Engine WLSE-1133.

ciscoASA5550  OBJECT IDENTIFIER
    ::= { ciscoProducts 753 }

-- Cisco Adaptive Security Appliance 5550

ciscoNMAONK9  OBJECT IDENTIFIER
    ::= { ciscoProducts 754 }

-- Cisco 2600/3700/ISR AON Module (NM-AON-K9)

ciscoNMAONWS  OBJECT IDENTIFIER
    ::= { ciscoProducts 755 }

-- Catalyst 6500 Series AON Module (WS-SVC-AON-1-K9)

ciscoNMAONAPS  OBJECT IDENTIFIER
    ::= { ciscoProducts 756 }

-- Cisco AON 8300 Series Appliance (APL-AON-8340-K9)

ciscoWae612K9  OBJECT IDENTIFIER
    ::= { ciscoProducts 757 }

-- Cisco Wide Area Engine Model WAE-612-K9

ciscoAIRAP1250  OBJECT IDENTIFIER
    ::= { ciscoProducts 758 }

-- 1250 series WLAN Access Point with one 10/100/1000TX port and dual IEEE 802.11a/b/g/n slots

ciscoCe512K9  OBJECT IDENTIFIER
    ::= { ciscoProducts 759 }

-- Cisco Content Engine CE-512-K9

ciscoFe512K9  OBJECT IDENTIFIER
    ::= { ciscoProducts 760 }

-- Cisco File Engine Model FE-512-K9

ciscoCe612K9  OBJECT IDENTIFIER
    ::= { ciscoProducts 761 }

-- Cisco Content Engine Model CE-612-K9

ciscoFe612K9  OBJECT IDENTIFIER
    ::= { ciscoProducts 762 }

-- Cisco File Engine Model FE-612-K9

ciscoASA5550sc  OBJECT IDENTIFIER
    ::= { ciscoProducts 763 }

-- Cisco Adaptive Security Appliance 5550 Security Context

ciscoASA5520sy  OBJECT IDENTIFIER
    ::= { ciscoProducts 764 }

-- Cisco Adaptive Security Appliance 5520 System Context

ciscoASA5540sy  OBJECT IDENTIFIER
    ::= { ciscoProducts 765 }

-- Cisco Adaptive Security Appliance 5540 System Context

ciscoASA5550sy  OBJECT IDENTIFIER
    ::= { ciscoProducts 766 }

-- Cisco Adaptive Security Appliance 5550 System Context

ciscoWsSvcFwm1sy  OBJECT IDENTIFIER
    ::= { ciscoProducts 767 }

-- Firewall Services Module for Catalyst 6500 Series System Context

ciscoPIXFirewall515sy  OBJECT IDENTIFIER
    ::= { ciscoProducts 768 }

-- Cisco PIX Firewall 515 System Context

ciscoPIXFirewall515Esy  OBJECT IDENTIFIER
    ::= { ciscoProducts 769 }

-- Cisco PIX Firewall 515E System Context

ciscoPIXFirewall525sy  OBJECT IDENTIFIER
    ::= { ciscoProducts 770 }

-- Cisco PIX Firewall 525 System Context

ciscoPIXFirewall535sy  OBJECT IDENTIFIER
    ::= { ciscoProducts 771 }

-- Cisco PIX Firewall 535 System Context

ciscoIpRanOpt4p  OBJECT IDENTIFIER
    ::= { ciscoProducts 772 }

-- The Mobile Wireless IP-RAN 4-Processor card for ONS platform with 4 Gigabit Ethernet ports

ciscoASA5510sc  OBJECT IDENTIFIER
    ::= { ciscoProducts 773 }

-- Cisco Adaptive Security Appliance 5510 Security Context

ciscoASA5510sy  OBJECT IDENTIFIER
    ::= { ciscoProducts 774 }

-- Cisco Adaptive Security Appliance 5510 System

ciscoJumpgate  OBJECT IDENTIFIER
    ::= { ciscoProducts 775 }


ciscoOe512K9  OBJECT IDENTIFIER
    ::= { ciscoProducts 776 }

-- Cisco Optimization Engine Model OE-512-K9

ciscoOe612K9  OBJECT IDENTIFIER
    ::= { ciscoProducts 777 }

-- Cisco Optimization Engine Model OE-612-K9

catalyst3750G24WS25  OBJECT IDENTIFIER
    ::= { ciscoProducts 778 }

-- Catalyst 3750 Unified Access Switch with 24 10/100/1000 Power over Ethernet ports + 2 Gigabit Ethernet SFP ports and integrated Wireless Controller supporting up to 25 Access Points

catalyst3750G24WS50  OBJECT IDENTIFIER
    ::= { ciscoProducts 779 }

-- Catalyst 3750 Unified Access Switch with 24 10/100/1000 Power over Ethernet ports + 2 Gigabit Ethernet SFP ports and integrated Wireless Controller supporting up to 50 Access Points

ciscoMe3400g12CsA  OBJECT IDENTIFIER
    ::= { ciscoProducts 780 }

-- Metro Ethernet 3400, 12 GE/SFP ports + 4 SFP ports fixed configuration Layer 2/3 Ethernet switch, AC power

ciscoMe3400g12CsD  OBJECT IDENTIFIER
    ::= { ciscoProducts 781 }

-- Metro Ethernet 3400, 12 GE/SFP ports + 4 SFP ports fixed configuration Layer 2/3 Ethernet switch, DC power

cisco877M  OBJECT IDENTIFIER
    ::= { ciscoProducts 782 }

-- Cisco 877 platform with 1 ADSL Annex M over POTS WAN interface, 4-port 10/100 BASE-T LAN Ethernet switch, hardware encryption and an optional Wireless LAN card

cisco1801M  OBJECT IDENTIFIER
    ::= { ciscoProducts 783 }

-- Cisco 1800 platform with 1 ADSL Annex M over POTS WAN interface, 8-port 10/100 BASE-T LAN Ethernet switch, 1 ISDN BRI S/T interface and an optional Wireless LAN

catalystWsCBS3040FSC  OBJECT IDENTIFIER
    ::= { ciscoProducts 784 }

-- Cisco Catalyst Blade Switch 3040 for FSC

ciscoOe511K9  OBJECT IDENTIFIER
    ::= { ciscoProducts 785 }

-- Cisco Optimization Engine Model OE-511-K9

ciscoOe611K9  OBJECT IDENTIFIER
    ::= { ciscoProducts 786 }

-- Cisco Optimization Engine Model OE-611-K9

ciscoOe7326K9  OBJECT IDENTIFIER
    ::= { ciscoProducts 787 }

-- Cisco Optimization Engine Model OE-7326-K9

ciscoMe492410GE  OBJECT IDENTIFIER
    ::= { ciscoProducts 788 }

-- Metro Ethernet fixed configuration box with 2 Ten Gigabit X2 ports and 24+4 One Gigabit SFP ports

catalyst3750E24TD  OBJECT IDENTIFIER
    ::= { ciscoProducts 789 }

-- Catalyst 3750E 24 10/100/1000 ports + 2 TenGigabit Ethernet (X2) ports fixed configuration Layer 2/Layer 3 Ethernet Stackable switch.

catalyst3750E48TD  OBJECT IDENTIFIER
    ::= { ciscoProducts 790 }

-- Catalyst 3750E 48 10/100/1000 ports + 2 TenGigabit Ethernet (X2) ports fixed configuration Layer 2/Layer 3 Ethernet Stackable switch.

catalyst3750E48PD  OBJECT IDENTIFIER
    ::= { ciscoProducts 791 }

-- Catalyst 3750E 48 10/100/1000 Power over Ethernet ports + 2 TenGigabit Ethernet (X2) ports fixed configuration Layer 2/Layer 3 Ethernet Stackable switch.

catalyst3750E24PD  OBJECT IDENTIFIER
    ::= { ciscoProducts 792 }

-- Catalyst 3750E 24 10/100/1000 Power over Ethernet ports + 2 TenGigabit Ethernet (X2) ports fixed configuration Layer 2/Layer 3 Ethernet Stackable switch.

catalyst3560E24TD  OBJECT IDENTIFIER
    ::= { ciscoProducts 793 }

-- Catalyst 3560E 24 10/100/1000 ports + 2 TenGigabit Ethernet (X2) ports fixed configuration Layer 2/Layer 3 Ethernet switch.

catalyst3560E48TD  OBJECT IDENTIFIER
    ::= { ciscoProducts 794 }

-- Catalyst 3560E 48 10/100/1000 ports + 2 TenGigabit Ethernet (X2) ports fixed configuration Layer 2/Layer 3 Ethernet switch.

catalyst3560E24PD  OBJECT IDENTIFIER
    ::= { ciscoProducts 795 }

-- Catalyst 3560E 24 10/100/1000 Power over Ethernet ports + 2 TenGigabit Ethernet (X2) ports fixed configuration Layer 2/Layer 3 Ethernet switch.

catalyst3560E48PD  OBJECT IDENTIFIER
    ::= { ciscoProducts 796 }

-- Catalyst 3560E 48 10/100/1000 Power over Ethernet ports + 2 TenGigabit Ethernet (X2) ports fixed configuration Layer 2/Layer 3 Ethernet switch.

catalyst35608PC  OBJECT IDENTIFIER
    ::= { ciscoProducts 797 }

-- Catalyst 3560 8 10/100 Power over Ethernet ports + 1  dual purpose Gigabit Ethernet port fixed configuration Layer 2 /Layer 3 Ethernet switch

catalyst29608TC  OBJECT IDENTIFIER
    ::= { ciscoProducts 798 }

-- Catalyst 2960 8 10/100 ports + 1  dual purpose Gigabit Ethernet port fixed configuration Layer 2 Ethernet switch

catalyst2960G8TC  OBJECT IDENTIFIER
    ::= { ciscoProducts 799 }

-- Catalyst 2960 7 10/100/1000 ports + 1  dual purpose Gigabit Ethernet port fixed configuration Layer 2 Ethernet switch

ciscoTSPri  OBJECT IDENTIFIER
    ::= { ciscoProducts 800 }

-- Cisco TelePresence Primary Codec

ciscoTSSec  OBJECT IDENTIFIER
    ::= { ciscoProducts 801 }

-- Cisco TelePresence Secondary Codec

ciscoUWIpPhone7921G  OBJECT IDENTIFIER
    ::= { ciscoProducts 802 }

-- Cisco Unified Wireless IP Phone 7921G with IEEE 802.11a/b/g interface

ciscoUWIpPhone7920  OBJECT IDENTIFIER
    ::= { ciscoProducts 803 }

-- Cisco Unified Wireless IP Phone 7920 with IEEE 802.11b interface

cisco3200WirelessMic  OBJECT IDENTIFIER
    ::= { ciscoProducts 804 }

-- Cisco 3200 Wireless Mobile Interface Card

ciscoISRWireless  OBJECT IDENTIFIER
    ::= { ciscoProducts 805 }

-- Cisco Integrated Services Router with Wireless

ciscoIPSVirtual  OBJECT IDENTIFIER
    ::= { ciscoProducts 806 }

-- Cisco Intrusion Prevention System virtual sensor

ciscoIDS4215Virtual  OBJECT IDENTIFIER
    ::= { ciscoProducts 807 }

-- Cisco Intrusion Detection System 4215 virtual sensor

ciscoIDS4235Virtual  OBJECT IDENTIFIER
    ::= { ciscoProducts 808 }

-- Cisco Intrusion Detection System 4235 virtual sensor

ciscoIDS4250Virtual  OBJECT IDENTIFIER
    ::= { ciscoProducts 809 }

-- Cisco Intrusion Detection System 4250 virtual sensor

ciscoIDS4250SXVirtual  OBJECT IDENTIFIER
    ::= { ciscoProducts 810 }

-- Cisco Intrusion Detection System 4250 SX virtual sensor

ciscoIDS4250XLVirtual  OBJECT IDENTIFIER
    ::= { ciscoProducts 811 }

-- Cisco Intrusion Detection System 4250 XL virtual sensor

ciscoIDS4240Virtual  OBJECT IDENTIFIER
    ::= { ciscoProducts 812 }

-- Cisco Intrusion Prevention Detection System 4240 virtual sensor

ciscoIDS4255Virtual  OBJECT IDENTIFIER
    ::= { ciscoProducts 813 }

-- Cisco Intrusion Prevention Detection System 4255 virtual sensor

ciscoIDS4260Virtual  OBJECT IDENTIFIER
    ::= { ciscoProducts 814 }

-- Cisco Intrusion Prevention Detection System 4260 virtual sensor

ciscoIDSIDSM2Virtual  OBJECT IDENTIFIER
    ::= { ciscoProducts 815 }

-- Cisco Intrusion Detection System Module IDSM2 virtual sensor

ciscoIPSSSM20Virtual  OBJECT IDENTIFIER
    ::= { ciscoProducts 816 }

-- Cisco Intrusion Prevention System Security Service Module SSM-20 virtual sensor

ciscoIPSSSM10Virtual  OBJECT IDENTIFIER
    ::= { ciscoProducts 817 }

-- Cisco Intrusion Prevention System Security Service Module SSM-10 virtual sensor

ciscoNMWLCE  OBJECT IDENTIFIER
    ::= { ciscoProducts 818 }

-- Integrated service router series 28xx/38xx with Wireless Lan Controller Network Module.

cisco3205WirelessMic  OBJECT IDENTIFIER
    ::= { ciscoProducts 819 }

-- Cisco 3205 Wireless MIC (Mobile Interface card) with 802.11a wireless interface in the PC104+ form factor. An interface card for the existing MAR 3200 products(Mobile Access Router)

cisco5720  OBJECT IDENTIFIER
    ::= { ciscoProducts 820 }

-- Integrated Encryption Router

cisco7201  OBJECT IDENTIFIER
    ::= { ciscoProducts 821 }

-- Cisco 7201 platform, 1 Rack Unit (RU) application specific router with 1 slot

ciscoCrs14S  OBJECT IDENTIFIER
    ::= { ciscoProducts 822 }

-- Cisco CRS-1 Series 4 Slots System

ciscoNmWae  OBJECT IDENTIFIER
    ::= { ciscoProducts 823 }

-- Wide Area Application Engine Network Module

ciscoACE4710K9  OBJECT IDENTIFIER
    ::= { ciscoProducts 824 }

-- ACE 4710 Application Control Engine Appliance

ciscoMe3400g2csA  OBJECT IDENTIFIER
    ::= { ciscoProducts 825 }

-- Metro Ethernet 3400, 2 GE/SFP ports + 2 SFP ports fixed configuration Layer 2/3 Ethernet switch, AC power

ciscoNmeNam  OBJECT IDENTIFIER
    ::= { ciscoProducts 826 }

-- Cisco NME-NAM, Network Analysis Module (NAM) for the branch office routers

ciscoUbr7225Vxr  OBJECT IDENTIFIER
    ::= { ciscoProducts 827 }

-- Cisco 7225 Universal Broadband Router, VXR series

ciscoAirWlc2106K9  OBJECT IDENTIFIER
    ::= { ciscoProducts 828 }

-- This is a replacement for device WLAN Controller with product name WLC2006.

ciscoMwr1951DC  OBJECT IDENTIFIER
    ::= { ciscoProducts 829 }


ciscoIPS4270  OBJECT IDENTIFIER
    ::= { ciscoProducts 830 }

-- IPS 4270 Intrusion Prevention Sensor

ciscoIPS4270Virtual  OBJECT IDENTIFIER
    ::= { ciscoProducts 831 }

-- IPS 4270 Intrusion Prevention Virtual Sensor

ciscoWSC6509ve  OBJECT IDENTIFIER
    ::= { ciscoProducts 832 }

-- Catalyst 6500 enhanced 9-slot vertical chassis

cisco5740  OBJECT IDENTIFIER
    ::= { ciscoProducts 833 }

-- Integrated Encryption Router

cisco861  OBJECT IDENTIFIER
    ::= { ciscoProducts 834 }

-- c861 with 1 FE, 4 switch ports, 1 Console/Aux port, and an optional Wireless LAN

cisco866  OBJECT IDENTIFIER
    ::= { ciscoProducts 835 }


cisco867  OBJECT IDENTIFIER
    ::= { ciscoProducts 836 }

-- c867 with 1 ADSL2/2+ AnnexA,4 switch ports, 1 Console/Aux port, and an optional Wireless LAN

cisco881  OBJECT IDENTIFIER
    ::= { ciscoProducts 837 }

-- c881 with 1 FE, 4 switch ports, 1 USB 1.1 port, 1 Console/Aux port, and an optional Wireless LAN.

cisco881G  OBJECT IDENTIFIER
    ::= { ciscoProducts 838 }

-- c881G with 1 FE, 4 switch ports, 1 USB 2.0 port, 1 Console/Aux port, 1 3G PCMCIA slot, and an optional Wireless LAN

ciscoIad881F  OBJECT IDENTIFIER
    ::= { ciscoProducts 839 }

-- IAD881IF with 1 FE, 4 switch ports, 1 USB 1.1 port, 1 Console/Aux port, 4 FXS ports, and an optional Wireless LAN

cisco881Srst  OBJECT IDENTIFIER
    ::= { ciscoProducts 840 }

-- c881SRST with 1 FE, 4 switch ports, 1 USB 1.1 port, 1 Console/Aux port, 4 FXS ports, 1 PSTN FXO port, and an optional Wireless LAN

ciscoIad881B  OBJECT IDENTIFIER
    ::= { ciscoProducts 841 }

-- IAD881B with 1 FE, 4 switch ports, 1 USB 1.1 port, 1 Console/Aux port, 2 PBX BRI ports, and an optional Wireless LAN

cisco886  OBJECT IDENTIFIER
    ::= { ciscoProducts 842 }

-- c886 with 1 ADSL2/2+ AnnexB, 4 switch ports, 1 USB 1.1 port, 1 Console/Aux port, 1 ISDN, and an optional Wireless LAN

cisco886G  OBJECT IDENTIFIER
    ::= { ciscoProducts 843 }

-- c886G with 1 ADSL2/2+ AnnexB,4 switch ports, 1 USB 2.0 port, 1 Console/Aux port, 1 3G PCMCIA slot, and an optional Wireless LAN

ciscoIad886F  OBJECT IDENTIFIER
    ::= { ciscoProducts 844 }

-- IAD886F with 1 ADSL2/2+ AnnexB, 4 switch ports, 1 USB 1.1 port, 1 Console/Aux port, 1 ISDN, 4 FXS ports, and an optional Wireless LAN

ciscoIad886B  OBJECT IDENTIFIER
    ::= { ciscoProducts 845 }

-- IAD886B with 1 ADSL2/2+ AnnexB, 4 switch ports, 1 USB 1.1 port, 1 Console/Aux port, 1 ISDN, 2 PBX BRI ports, and an optional Wireless LAN

cisco886Srst  OBJECT IDENTIFIER
    ::= { ciscoProducts 846 }

-- c886SRST with 1 ADSL2/2+ Annex B, 4 switch ports, 1 USB 1.1 port, 1 Console/Aux port, 4 FXS ports, 1 PSTN BRI port, and an optional Wireless LAN

cisco887  OBJECT IDENTIFIER
    ::= { ciscoProducts 847 }

-- c887 with 1 ADSL2/2+ AnnexA, 4 switch ports, 1 USB 1.1 port, 1 Console/Aux port, 1 ISDN, and an optional Wireless LAN

cisco887G  OBJECT IDENTIFIER
    ::= { ciscoProducts 848 }

-- c887G with 1 ADSL2/2+ AnnexA,4 switch ports, 1 USB 2.0 port, 1 Console/Aux port, 1 3G PCMCIA slot, and an optional Wireless LAN

ciscoIad887F  OBJECT IDENTIFIER
    ::= { ciscoProducts 849 }

-- IAD887 with 1 ADSL2/2+ AnnexA, 4 switch ports, 1 USB 1.1 port, 1 Console/Aux port, 1 ISDN, 4 FXS ports, and an optional Wireless LAN

ciscoIad887B  OBJECT IDENTIFIER
    ::= { ciscoProducts 850 }

-- IAD887B with 1 ADSL2/2+ AnnexA, 4 switch ports, 1 USB 1.1 port, 1 Console/Aux port, 1 ISDN, 2 PBX BRI ports, and an optional Wireless LAN

cisco887Srst  OBJECT IDENTIFIER
    ::= { ciscoProducts 851 }

-- c887SRST with 1 ADSL2/2+ AnnexA, 4 switch ports, 1 USB 1.1 port, 1 Console/Aux port, 4 FXS ports, 1 PSTN BRI port, and an optional Wireless LAN

cisco888  OBJECT IDENTIFIER
    ::= { ciscoProducts 852 }

-- c888 with 1 G.SHDSL, 4 switch ports, 1 USB 1.1 port, 1 Console/Aux port, 1 ISDN, and an optional Wireless LAN.

cisco888G  OBJECT IDENTIFIER
    ::= { ciscoProducts 853 }

-- c888G with 1 G.SHDSL, 4 switch ports, 1 USB 2.0 port, 1 Console/Aux port, 1 3G PCMCIA slot, and an optional Wireless LAN

ciscoIad888F  OBJECT IDENTIFIER
    ::= { ciscoProducts 854 }

-- IAD888F with 1 G.SHDSL, 4 switch ports, 1 USB 1.1 port, 1 Console/Aux port, 1 ISDN, 4 FXS ports, and an optional Wireless LAN

ciscoIad888B  OBJECT IDENTIFIER
    ::= { ciscoProducts 855 }

-- IAD888B with 1 G.SHDSL, 4 switch ports, 1 USB 1.1 port, 1 Console/Aux port, 1 ISDN, 2 PBX BRI ports, and an optional Wireless LAN

cisco888Srst  OBJECT IDENTIFIER
    ::= { ciscoProducts 856 }

-- c888SRST with 1 G.SHDSL, 4 switch ports, 1 USB 1.1 port, 1 Console/Aux port, 4 FXS ports, 1 PSTN BRI port, and an optional Wireless LAN

cisco891  OBJECT IDENTIFIER
    ::= { ciscoProducts 857 }

-- c891 with 1 GE, 8 switch ports, 2 USB 2.0 ports, 2 Console/Aux ports, 1 V.92, 1 Backup FE, and an optional Wireless LAN

cisco892  OBJECT IDENTIFIER
    ::= { ciscoProducts 858 }

-- c892 with 1GE, 8 switch ports, 2 USB 2.0 ports, 2 Console/Aux ports, 1 ISDN, 1 Backup FE, and an optional Wireless LAN

cisco885D3  OBJECT IDENTIFIER
    ::= { ciscoProducts 859 }


ciscoIad885FD3  OBJECT IDENTIFIER
    ::= { ciscoProducts 860 }


cisco885EJ3  OBJECT IDENTIFIER
    ::= { ciscoProducts 861 }


cisco7603s  OBJECT IDENTIFIER
    ::= { ciscoProducts 862 }

-- Cisco 7600 S-Series Chassis with 3 slots

cisco7606s  OBJECT IDENTIFIER
    ::= { ciscoProducts 863 }

-- Cisco 7600 S-Series Chassis with 6 slots

cisco7609s  OBJECT IDENTIFIER
    ::= { ciscoProducts 864 }

-- Cisco 7600 S-Series Chassis with 9 slots

cisco7600Seb  OBJECT IDENTIFIER
    ::= { ciscoProducts 865 }


ciscoNMECUE  OBJECT IDENTIFIER
    ::= { ciscoProducts 866 }

-- Cisco Unity Express Network Module Enhanced (NME-CUE)

ciscoAIM2CUE  OBJECT IDENTIFIER
    ::= { ciscoProducts 867 }

-- Cisco Unity Express advanced integration module 2 (AIM2-CUE)

ciscoUC500  OBJECT IDENTIFIER
    ::= { ciscoProducts 868 }

-- Unified Communication 500 Series (UC500)

cisco860Ap  OBJECT IDENTIFIER
    ::= { ciscoProducts 869 }

-- Cisco 860 AP is the embedded wireless access point module for Cisco 860 router. It has one IEEE 802.11 b/g/n radio port which operates in 2.4 GHz.

cisco880Ap  OBJECT IDENTIFIER
    ::= { ciscoProducts 870 }

-- Cisco 880 AP is the embedded wireless access point module for Cisco 880 router. It has one IEEE 802.11 b/g/n radio port which operates in 2.4 GHz.

cisco890Ap  OBJECT IDENTIFIER
    ::= { ciscoProducts 871 }

-- Cisco 890 AP is the embedded wireless access point module for Cisco 890 router. It has one IEEE 802.11 b/g/n radio port which operates in 2.4 GHz and one IEEE 802.11 a/n radio port which operates in 5 GHz

cisco1900Ap  OBJECT IDENTIFIER
    ::= { ciscoProducts 872 }

-- Cisco 1900 AP is the embedded wireless access point module for Cisco 1900 router. It has one IEEE 802.11 b/g/n radio port which operates in 2.4 GHz and one IEEE 802.11 a/n radio port which operates in 5 GHz

cisco340024FSA  OBJECT IDENTIFIER
    ::= { ciscoProducts 873 }

-- Metro Ethernet 3400, 24 100BaseFX Fast Ethernet + 2 SFP ports fixed configuration Layer 2/3 Ethernet switch

catalyst4503e  OBJECT IDENTIFIER
    ::= { ciscoProducts 874 }

-- Catalyst 4500 E-series with 3 slots (WS-C4503-E)

catalyst4506e  OBJECT IDENTIFIER
    ::= { ciscoProducts 875 }

-- Catalyst 4500 E-series with 6 slots (WS-C4506-E)

catalyst4507re  OBJECT IDENTIFIER
    ::= { ciscoProducts 876 }

-- Catalyst 4500 E-series with 7 slots (WS-C4507R-E)

catalyst4510re  OBJECT IDENTIFIER
    ::= { ciscoProducts 877 }

-- Catalyst 4500 E-series with 10 slots (WS-C4510R-E)

ciscoUC520s8U4FXOK9  OBJECT IDENTIFIER
    ::= { ciscoProducts 878 }

-- UC500 with support for 8 switch ports and 4 FXO ports

ciscoUC520s8U4FXOWK9  OBJECT IDENTIFIER
    ::= { ciscoProducts 879 }

-- UC500 with support for 8 switch ports, 4 FXO ports, and Wi-Fi

ciscoUC520s8U2BRIK9  OBJECT IDENTIFIER
    ::= { ciscoProducts 880 }

-- UC500 with support for 8 switch ports and 2 BRI

ciscoUC520s8U2BRIWK9  OBJECT IDENTIFIER
    ::= { ciscoProducts 881 }

-- UC500 with support for 8 switch ports and 2 BRI, and Wi-Fi

ciscoUC520s16U4FXOK9  OBJECT IDENTIFIER
    ::= { ciscoProducts 882 }

-- UC500 with support for 16 switch ports and 4 FXO ports

ciscoUC520s16U4FXOWK9  OBJECT IDENTIFIER
    ::= { ciscoProducts 883 }

-- UC500 with support for 16 switch ports, 4 FXO ports, and Wi-Fi

ciscoUC520s16U2BRIK9  OBJECT IDENTIFIER
    ::= { ciscoProducts 884 }

-- UC500 with support for 16 switch ports and 2 BRI

ciscoUC520s16U2BRIWK9  OBJECT IDENTIFIER
    ::= { ciscoProducts 885 }

-- UC500 with support for 16 switch ports and 2 BRI, and Wi-Fi

ciscoUC520m32U8FXOK9  OBJECT IDENTIFIER
    ::= { ciscoProducts 886 }

-- UC500 with support for 32 switch ports and 8 FXO ports

ciscoUC520m32U8FXOWK9  OBJECT IDENTIFIER
    ::= { ciscoProducts 887 }

-- UC500 with support for 32 switch ports and 8 FXO ports, and Wi-Fi

ciscoUC520m32U4BRIK9  OBJECT IDENTIFIER
    ::= { ciscoProducts 888 }

-- UC500 with support for 32 switch ports and 4 BRI

ciscoUC520m32U4BRIWK9  OBJECT IDENTIFIER
    ::= { ciscoProducts 889 }

-- UC500 with support for 32 switch ports and 4 BRI, and Wi-Fi

ciscoUC520m48U12FXOK9  OBJECT IDENTIFIER
    ::= { ciscoProducts 890 }

-- UC500 with support for 48 switch ports and 12 FXO ports

ciscoUC520m48U12FXOWK9  OBJECT IDENTIFIER
    ::= { ciscoProducts 891 }

-- UC500 with support for 48 switch ports and 12 FXO ports, and Wi-Fi

ciscoUC520m48U6BRIK9  OBJECT IDENTIFIER
    ::= { ciscoProducts 892 }

-- UC500 with support for 48 switch ports and 6 BRI

ciscoUC520m48U6BRIWK9  OBJECT IDENTIFIER
    ::= { ciscoProducts 893 }

-- UC500 with support for 48 switch ports and 6 BRI, and Wi-Fi

ciscoUC520m48U1T1E1FK9  OBJECT IDENTIFIER
    ::= { ciscoProducts 894 }

-- UC500 with support for 48 switch ports and 1 T1

ciscoUC520m48U1T1E1BK9  OBJECT IDENTIFIER
    ::= { ciscoProducts 895 }

-- UC500 with support for 48 switch ports and 1 T1, and Wi-Fi

catalyst65xxVirtualSwitch  OBJECT IDENTIFIER
    ::= { ciscoProducts 896 }

-- 65xx Virtual sSwitch

catalystExpress5208PC  OBJECT IDENTIFIER
    ::= { ciscoProducts 897 }

-- Catalyst Express 520 8 10/100 Power over Ethernet ports + 1 dual purpose Gigabit Ethernet port fixed configuration Layer 2 Ethernet switch

ciscoMCS7816I  OBJECT IDENTIFIER
    ::= { ciscoProducts 898 }

-- Cisco Media Convergence Server 7816 (IBM)

ciscoMCS7828I  OBJECT IDENTIFIER
    ::= { ciscoProducts 899 }

-- Cisco Media Convergence Server 7828 (IBM)

ciscoMCS7816H  OBJECT IDENTIFIER
    ::= { ciscoProducts 900 }

-- Cisco Media Convergence Server 7816 (HP)

ciscoMCS7828H  OBJECT IDENTIFIER
    ::= { ciscoProducts 901 }

-- Cisco Media Convergence Server 7828 (HP)

cisco1861Uc2BK9  OBJECT IDENTIFIER
    ::= { ciscoProducts 902 }

-- C1861 UC with support for 2 BRI ports and CUE

cisco1861Uc4FK9  OBJECT IDENTIFIER
    ::= { ciscoProducts 903 }

-- C1861 UC with support for 4 FXO ports and CUE

cisco1861Srst2BK9  OBJECT IDENTIFIER
    ::= { ciscoProducts 904 }

-- C1861 SRST with support for 2BRI ports

cisco1861Srst4FK9  OBJECT IDENTIFIER
    ::= { ciscoProducts 905 }

-- C1861 SRST with support for 4 FXO ports

ciscoNmeApa  OBJECT IDENTIFIER
    ::= { ciscoProducts 906 }

-- Integrated Service Engine for Application Performance Assurance.

ciscoOe7330K9  OBJECT IDENTIFIER
    ::= { ciscoProducts 907 }

-- Cisco Optimization Engine Model OE-7330-K9

ciscoOe7350K9  OBJECT IDENTIFIER
    ::= { ciscoProducts 908 }

-- Cisco Optimization Engine Model OE-7350-K9

ciscoWsCbs3110gS  OBJECT IDENTIFIER
    ::= { ciscoProducts 909 }


ciscoWsCbs3110gSt  OBJECT IDENTIFIER
    ::= { ciscoProducts 910 }


ciscoWsCbs3110xS  OBJECT IDENTIFIER
    ::= { ciscoProducts 911 }


ciscoWsCbs3110xSt  OBJECT IDENTIFIER
    ::= { ciscoProducts 912 }


ciscoSce8000  OBJECT IDENTIFIER
    ::= { ciscoProducts 913 }

-- Cisco SCE8000 Service Control Engine

ciscoASA5580  OBJECT IDENTIFIER
    ::= { ciscoProducts 914 }

-- Cisco Adaptive Security Appliance 5580

ciscoASA5580sc  OBJECT IDENTIFIER
    ::= { ciscoProducts 915 }

-- Cisco Adaptive Security Appliance 5580 Security Context

ciscoASA5580sy  OBJECT IDENTIFIER
    ::= { ciscoProducts 916 }

-- Cisco Adaptive Security Appliance 5580 System Context

cat4900M  OBJECT IDENTIFIER
    ::= { ciscoProducts 917 }

-- Catalyst 4900M series chassis with fixed 8 10Gig port base system with 2 additional half height line card slots ( WS-C4900M )

catWsCbs3120gS  OBJECT IDENTIFIER
    ::= { ciscoProducts 918 }


catWsCbs3120xS  OBJECT IDENTIFIER
    ::= { ciscoProducts 919 }


catWsCbs3032Del  OBJECT IDENTIFIER
    ::= { ciscoProducts 920 }

-- WS-CBS3032-DEL: Cisco Catalyst Stackable Blade Switch for FSC with 8 1Gigabit Uplink ports

catWsCbs3130gS  OBJECT IDENTIFIER
    ::= { ciscoProducts 921 }


catWsCbs3130xS  OBJECT IDENTIFIER
    ::= { ciscoProducts 922 }


ciscoASR1002  OBJECT IDENTIFIER
    ::= { ciscoProducts 923 }

-- Cisco Aggregation Services Router 1000 Series with 2RU Chassis

ciscoASR1004  OBJECT IDENTIFIER
    ::= { ciscoProducts 924 }

-- Cisco Aggregation Services Router 1000 Series With 4RU Chassis

ciscoASR1006  OBJECT IDENTIFIER
    ::= { ciscoProducts 925 }

-- Cisco Aggregation Services Router 1000 Series With 6RU Chassis

cisco520WirelessController  OBJECT IDENTIFIER
    ::= { ciscoProducts 926 }

-- Cisco 500 series Wireless controller for Small Medium Business Market

cat296048TCS  OBJECT IDENTIFIER
    ::= { ciscoProducts 927 }

-- Catalyst 2960 48 10/100 ports plus 2 dual purpose Gigabit Ethernet ports fixed configuration Layer 2 Ethernet switch

cat296024TCS  OBJECT IDENTIFIER
    ::= { ciscoProducts 928 }

-- Catalyst 2960 24 10/100 ports plus 2 dual purpose Gigabit Ethernet ports fixed configuration Layer 2 Ethernet switch

cat296024S  OBJECT IDENTIFIER
    ::= { ciscoProducts 929 }

-- Catalyst 2960 24 10/100 ports Layer 2 Ethernet switch

cat3560e12d  OBJECT IDENTIFIER
    ::= { ciscoProducts 930 }

-- Catalyst 3560E 12 Ten GE (X2) ports

ciscoCatRfgw  OBJECT IDENTIFIER
    ::= { ciscoProducts 931 }

-- Cisco RF gateway, with 2SUP+10RF+2TCC+12RFSW slots, Display, Fan Tray

catExpress52024TT  OBJECT IDENTIFIER
    ::= { ciscoProducts 932 }

-- Catalyst Express 520 24 10/100 ports + 2 Gigabit Ethernet ports fixed configuration Layer 2 Ethernet switch

catExpress52024LC  OBJECT IDENTIFIER
    ::= { ciscoProducts 933 }

-- Catalyst Express 520 24 10/100 ports (4 Power Over Ethernet Ports) + 2 dual purpose Gigabit Ethernet ports fixed configuration Layer 2 Ethernet switch

catExpress52024PC  OBJECT IDENTIFIER
    ::= { ciscoProducts 934 }

-- Catalyst Express 520 24 Power Over Ethernet Ports + 2 dual purpose Gigabit Ethernet ports fixed configuration Layer 2 Ethernet switch

catExpress520G24TC  OBJECT IDENTIFIER
    ::= { ciscoProducts 935 }

-- Catalyst Express 520 24 Gigabit Ethernet Ports + 2 dual purpose Gigabit Ethernet ports fixed configuration Layer 2 Ethernet switch

ciscoCDScde100  OBJECT IDENTIFIER
    ::= { ciscoProducts 936 }

-- Cisco Content Delivery System Model CDE-100

ciscoCDScde200  OBJECT IDENTIFIER
    ::= { ciscoProducts 937 }

-- Cisco Content Delivery System Model CDE-200

ciscoCDScde300  OBJECT IDENTIFIER
    ::= { ciscoProducts 938 }

-- Cisco Content Delivery System Model CDE-300

cisco1861SrstCue2BK9  OBJECT IDENTIFIER
    ::= { ciscoProducts 939 }

-- C1861 SRST with support for 2 BRI ports and CUE

cisco1861SrstCue4FK9  OBJECT IDENTIFIER
    ::= { ciscoProducts 940 }

-- C1861 SRST with support for 4 FXO ports and CUE

ciscoVFrameDataCenter  OBJECT IDENTIFIER
    ::= { ciscoProducts 941 }

-- Data center provisioning and virtualization

ciscoVQEServer  OBJECT IDENTIFIER
    ::= { ciscoProducts 942 }

-- Cisco VQE(Video Quality Experience) offers service providers a set of technologies and products associated with the delivery of IPTV video services.

ciscoIPSSSM40Virtual  OBJECT IDENTIFIER
    ::= { ciscoProducts 943 }

-- Cisco Intrusion Prevention  System Security Service Module SSM-40 Virtual Sensor

ciscoIPSSSM40  OBJECT IDENTIFIER
    ::= { ciscoProducts 944 }

-- Cisco Intrusion Prevention  System Security Service Module SSM-40 Sensor

ciscoVgd1t3  OBJECT IDENTIFIER
    ::= { ciscoProducts 945 }

-- VGD Voice Gateway with 1xCT3 supporting CCM and MGCP

ciscoCBS3100  OBJECT IDENTIFIER
    ::= { ciscoProducts 946 }


ciscoCBS3110  OBJECT IDENTIFIER
    ::= { ciscoProducts 947 }


ciscoCBS3120  OBJECT IDENTIFIER
    ::= { ciscoProducts 948 }


ciscoCBS3130  OBJECT IDENTIFIER
    ::= { ciscoProducts 949 }


catalyst296024PC  OBJECT IDENTIFIER
    ::= { ciscoProducts 950 }

-- 24 10/100 In-Line Power Ethernet ports plus 2 dual purpose Gigabit Ethernet ports

catalyst296024LT  OBJECT IDENTIFIER
    ::= { ciscoProducts 951 }

-- 24 10/100, 8 POE and 2T ports switch

catalyst2960PD8TT  OBJECT IDENTIFIER
    ::= { ciscoProducts 952 }

-- 8 10/100 ports plus 1T PD port switch

ciscoSpa2x1geSynce  OBJECT IDENTIFIER
    ::= { ciscoProducts 953 }


ciscoN5kC5020pBa  OBJECT IDENTIFIER
    ::= { ciscoProducts 954 }

-- N5020 Chassis, 1AC PS, 40 SFP+ Ports. Modules Sold Seperate

ciscoN5kC5020pBd  OBJECT IDENTIFIER
    ::= { ciscoProducts 955 }

-- N5020 Chassis, 1DC PS, 40 SFP+ Ports. Modules Sold Seperate

catalyst3560E12SD  OBJECT IDENTIFIER
    ::= { ciscoProducts 956 }

-- Catalyst 3560E, 12 SFP Gigabit Ethernet ports + 2 TenGigabit Ethernet (X2) ports

ciscoOe674  OBJECT IDENTIFIER
    ::= { ciscoProducts 957 }

-- Cisco Optimization Engine 674

ciscoIE30004TC  OBJECT IDENTIFIER
    ::= { ciscoProducts 958 }

-- Cisco Industrial Ethernet 3000 Switch, 4 10/100 + 2 T/SFP

ciscoIE30008TC  OBJECT IDENTIFIER
    ::= { ciscoProducts 959 }

-- Cisco Industrial Ethernet 3000 Switch, 8 10/100 + 2 T/SFP

ciscoRAIE1783MS06T  OBJECT IDENTIFIER
    ::= { ciscoProducts 960 }

-- Cisco Rockwell brand Industrial Ethernet  Switch, 4 10/100 + 2 T/SFP

ciscoRAIE1783MS10T  OBJECT IDENTIFIER
    ::= { ciscoProducts 961 }

-- Cisco Rockwell brand Industrial Ethernet Switch, 8 10/100 + 2 T/SFP

cisco2435Iad8fxs  OBJECT IDENTIFIER
    ::= { ciscoProducts 962 }

-- IAD2435 with 8FXS, 2FE and 1T1/E1

ciscoVG204  OBJECT IDENTIFIER
    ::= { ciscoProducts 963 }

-- Line side Analog Gateway with 4FXS Analog ports

ciscoVG202  OBJECT IDENTIFIER
    ::= { ciscoProducts 964 }

-- Line side Analog Gateway with 2FXS Analog ports

catalyst291824TT  OBJECT IDENTIFIER
    ::= { ciscoProducts 965 }

-- Catalyst 2918 24 10/100 ports + 2 10/100/1000 Ethernet ports fixed configuration Layer 2 Ethernet switch

catalyst291824TC  OBJECT IDENTIFIER
    ::= { ciscoProducts 966 }

-- Catalyst 2918 24 10/100 ports + 2 dual purpose Gigabit Ethernet ports fixed configuration Layer 2 Ethernet switch

catalyst291848TT  OBJECT IDENTIFIER
    ::= { ciscoProducts 967 }

-- Catalyst 2918 48 10/100 ports + 2 10/100/1000 Ethernet ports fixed configuration Layer 2 Ethernet switch

catalyst291848TC  OBJECT IDENTIFIER
    ::= { ciscoProducts 968 }

-- Catalyst 2918 48 10/100 ports + 2 dual purpose Gigabit Ethernet ports fixed configuration Layer 2 Ethernet switch

ciscoVQETools  OBJECT IDENTIFIER
    ::= { ciscoProducts 969 }

-- Cisco CDE110 appliances hosting VQE Channel Provisioning Tool (VCPT) and VQE Client Channel Configuration Delivery Server

ciscoUC520m24U4BRIK9  OBJECT IDENTIFIER
    ::= { ciscoProducts 970 }

-- UC500 with support for 24U CME Base, CUE and Phone FL w/4BRI, 1VIC

ciscoUC520m24U8FXOK9  OBJECT IDENTIFIER
    ::= { ciscoProducts 971 }

-- UC500 with support for 24U CME Base, CUE and Phone FL w/8FXO, 1VIC

ciscoUC520s16U2BRIWK9J  OBJECT IDENTIFIER
    ::= { ciscoProducts 972 }

-- UC500 for Japan with support for 16 switch ports and 2 BRI, and Wi-Fi

ciscoUC520s8U2BRIWK9J  OBJECT IDENTIFIER
    ::= { ciscoProducts 973 }

-- UC500 for Japan with support for 8 switch ports and 2 BRI, and Wi-Fi

ciscoVSIntSp  OBJECT IDENTIFIER
    ::= { ciscoProducts 974 }

-- Cisco Video Stream Integrated Services

ciscoVSSP  OBJECT IDENTIFIER
    ::= { ciscoProducts 975 }

-- Cisco Video Stream Services Platform

ciscoVSHydecoder  OBJECT IDENTIFIER
    ::= { ciscoProducts 976 }

-- Cisco Video Stream Hybrid Decoder

ciscoVSDecoder  OBJECT IDENTIFIER
    ::= { ciscoProducts 977 }

-- Cisco Video Stream Decoder

ciscoVSEncoder4P  OBJECT IDENTIFIER
    ::= { ciscoProducts 978 }

-- Cisco Video Stream Encoder 4 Port

ciscoVSEncoder1P  OBJECT IDENTIFIER
    ::= { ciscoProducts 979 }

-- Cisco Video Stream Encoder 1 Port

ciscoSCS1000K9  OBJECT IDENTIFIER
    ::= { ciscoProducts 980 }

-- Smart Care 1000 Series Network Appliance

cisco1805  OBJECT IDENTIFIER
    ::= { ciscoProducts 981 }

-- Cisco1805 is a repackaging effort for design to address the low end cable access market. C1805 is deployed as cut down and fixed version of Cisco C1841

ciscoCe7341  OBJECT IDENTIFIER
    ::= { ciscoProducts 982 }

-- Cisco Content Engine

ciscoCe7371  OBJECT IDENTIFIER
    ::= { ciscoProducts 983 }

-- Cisco Content Engine

cisco7613s  OBJECT IDENTIFIER
    ::= { ciscoProducts 984 }


ciscoOe574  OBJECT IDENTIFIER
    ::= { ciscoProducts 985 }

-- Cisco Optimization Engine 574

ciscoOe474  OBJECT IDENTIFIER
    ::= { ciscoProducts 986 }

-- Cisco Optimization Engine 474

ciscoOe274  OBJECT IDENTIFIER
    ::= { ciscoProducts 987 }

-- Cisco Optimization Engine 274

ciscoAp801agn  OBJECT IDENTIFIER
    ::= { ciscoProducts 988 }

-- Cisco AP801 Access Point with dual IEEE 802.11a/g/n radio ports

ciscoAp801gn  OBJECT IDENTIFIER
    ::= { ciscoProducts 989 }

-- Cisco AP801 Access Point with single IEEE 802.11g/n radio port

cisco1861WSrstCue4FK9  OBJECT IDENTIFIER
    ::= { ciscoProducts 990 }

-- C1861 SRST with support for 4 FXO ports, Wireless and CUE

cisco1861WSrstCue2BK9  OBJECT IDENTIFIER
    ::= { ciscoProducts 991 }

-- C1861 SRST with support for 2 BRI ports, Wireless and CUE

cisco1861WSrst4FK9  OBJECT IDENTIFIER
    ::= { ciscoProducts 992 }

-- C1861 SRST with support for 4 FXO ports and Wireless

cisco1861WSrst2BK9  OBJECT IDENTIFIER
    ::= { ciscoProducts 993 }

-- C1861 SRST with support for 2 BRI ports and Wireless

cisco1861WUc4FK9  OBJECT IDENTIFIER
    ::= { ciscoProducts 994 }

-- 1861 UC with support for 4 FXO ports, Wireless and CUE

cisco1861WUc2BK9  OBJECT IDENTIFIER
    ::= { ciscoProducts 995 }

-- 1861 UC with support for 2 BRI ports, Wireless and CUE

ciscoCe674  OBJECT IDENTIFIER
    ::= { ciscoProducts 996 }

-- Cisco Content Engine 674

ciscoVQEIST  OBJECT IDENTIFIER
    ::= { ciscoProducts 997 }

-- VQE-IST is an Integrated Server Tool that combines services from VQE Server and VQE Tools

ciscoAIRAP1160  OBJECT IDENTIFIER
    ::= { ciscoProducts 998 }


ciscoWsCbs3012Ibm  OBJECT IDENTIFIER
    ::= { ciscoProducts 999 }


ciscoWsCbs3012IbmI  OBJECT IDENTIFIER
    ::= { ciscoProducts 1000 }


ciscoWsCbs3125gS  OBJECT IDENTIFIER
    ::= { ciscoProducts 1001 }


ciscoWsCbs3125xS  OBJECT IDENTIFIER
    ::= { ciscoProducts 1002 }


ciscoTSPriG2  OBJECT IDENTIFIER
    ::= { ciscoProducts 1003 }

-- Cisco TelePresence Primary Codec, Generation 2

catalyst492810GE  OBJECT IDENTIFIER
    ::= { ciscoProducts 1004 }

-- Fixed configuration Catalyst 4000 with 28 1000BaseX SFP port

catalyst296048TTS  OBJECT IDENTIFIER
    ::= { ciscoProducts 1005 }

-- Catalyst 2960 48 10/100 ports + 2 10/100/1000 Ethernet ports fixed configuration Layer 2 Ethernet switch

catalyst29608TCS  OBJECT IDENTIFIER
    ::= { ciscoProducts 1006 }

-- Catalyst 2960 8 10/100 ports + 1 dual purpose Gigabit Ethernet port fixed configuration Layer 2 Ethernet switch

ciscoMe3400eg2csA  OBJECT IDENTIFIER
    ::= { ciscoProducts 1007 }

-- Metro Ethernet 3400E, 2 GE/SFP ports + 2 SFP ports fixed configuration Layer 2/3 Ethernet switch, AC power

ciscoMe3400eg12csM  OBJECT IDENTIFIER
    ::= { ciscoProducts 1008 }

-- Metro Ethernet 3400 , 12 GE/SFP ports + 4 SFP ports fixed configuration Layer 2/3 Ethernet switch, modular power

ciscoMe3400e24tsM  OBJECT IDENTIFIER
    ::= { ciscoProducts 1009 }

-- Metro Ethernet 3400E, 24 10/100 Fast Ethernet + 2 SFP ports fixed configuration Layer 2/3 Ethernet switch, modular power

ciscoIPSSSC5Virtual  OBJECT IDENTIFIER
    ::= { ciscoProducts 1010 }

-- Cisco Intrusion Prevention System Security Service Card SSC-5 Virtual Sensor

ciscoSR520FE  OBJECT IDENTIFIER
    ::= { ciscoProducts 1011 }

-- SR520 with 1 10/100T ethernet WAN interface, 4-port 10/100 Base-T LAN Ethernet switch, hardware encryption and an optional Wireless LAN card

ciscoSR520ADSL  OBJECT IDENTIFIER
    ::= { ciscoProducts 1012 }

-- SR520 with 1 ADSL over POTS WAN interface, 4-port 10/100 BASE-T LAN Ethernet switch, hardware encryption and an optional Wireless LAN card

ciscoSR520ADSLi  OBJECT IDENTIFIER
    ::= { ciscoProducts 1013 }

-- SR520 with 1 ADSL over ISDN WAN interface, 4-port 10/100 Base-T LAN Ethernet switch, hardware encryption and an optional Wireless LAN card

ciscoMwr2941DC  OBJECT IDENTIFIER
    ::= { ciscoProducts 1014 }

-- The Mobile Wireless router MWR-2941-DC is a router targeted at application in a cell site Base Transciever Station (BTS) providing Radio Access Network (RAN) optimization

catalyst356012PCS  OBJECT IDENTIFIER
    ::= { ciscoProducts 1015 }

-- Catalyst 3560 12 10/100 Power over Ethernet ports + 1 dual purpose Gigabit Ethernet port fixed configuration Layer 2 Ethernet switch

catalyst296048PSTL  OBJECT IDENTIFIER
    ::= { ciscoProducts 1016 }

-- Catalyst 2960 48 10/100 Power over Ethernet ports + 2 10/100/1000 Ethernet Ports + 2 SFP fixed configuration Layer 2 Ethernet switch

ciscoASR9010  OBJECT IDENTIFIER
    ::= { ciscoProducts 1017 }

-- Cisco Aggregation Services Router (ASR) 9010 Chassis

ciscoASR9006  OBJECT IDENTIFIER
    ::= { ciscoProducts 1018 }

-- Cisco Aggregation Services Router (ASR) 9006 Chassis

catalyst3560v224tsD  OBJECT IDENTIFIER
    ::= { ciscoProducts 1019 }

-- 24 10/100 ports + 2 Ethernet Gigabit SFP ports fixed configuration Layer 2/Layer 3 Ethernet Non-stackable switch, DC power

catalyst3560v224ts  OBJECT IDENTIFIER
    ::= { ciscoProducts 1020 }

-- 24 10/100 ports + 2 Ethernet Gigabit SFP ports fixed configuration Layer 2/Layer 3 Ethernet Non-stackable switch

catalyst3560v224ps  OBJECT IDENTIFIER
    ::= { ciscoProducts 1021 }

-- 24 10/100 ports + 2 Ethernet Gigabit SFP ports fixed configuration Layer 2/Layer 3 Ethernet Non-stackable PoE switch

catalyst3750v224ts  OBJECT IDENTIFIER
    ::= { ciscoProducts 1022 }

-- 24 10/100 ports + 2 Ethernet Gigabit SFP ports fixed configuration Layer 2/Layer 3 Ethernet Stackable switch

catalyst3750v224ps  OBJECT IDENTIFIER
    ::= { ciscoProducts 1023 }

-- 24 10/100 ports + 2 Ethernet Gigabit SFP ports fixed configuration Layer 2/Layer 3 Ethernet Stackable PoE switch

catalyst3560v248ts  OBJECT IDENTIFIER
    ::= { ciscoProducts 1024 }

-- 48 10/100 ports + 4 Ethernet Gigabit SFP ports fixed configuration Layer 2/Layer 3 Ethernet Non-stackable switch

catalyst3560v248ps  OBJECT IDENTIFIER
    ::= { ciscoProducts 1025 }

-- 48 10/100 ports + 4 Ethernet Gigabit SFP ports fixed configuration Layer 2/Layer 3 Ethernet Non-stackable PoE switch

catalyst3750v248ts  OBJECT IDENTIFIER
    ::= { ciscoProducts 1026 }

-- 48 10/100 ports + 4 Ethernet Gigabit SFP ports fixed configuration Layer 2/Layer 3 Ethernet Stackable switch

catalyst3750v248ps  OBJECT IDENTIFIER
    ::= { ciscoProducts 1027 }

-- 48 10/100 ports + 4 Ethernet Gigabit SFP ports fixed configuration Layer 2/Layer 3 Ethernet Stackable PoE switch

ciscoHwicCableD2  OBJECT IDENTIFIER
    ::= { ciscoProducts 1028 }

-- This HWIC supports DOCSIS 2.0 in modular Integrated Service Routers as well as IAD2430 series routers

ciscoHwicCableEJ2  OBJECT IDENTIFIER
    ::= { ciscoProducts 1029 }

-- This HWIC supports Euro-DOCSIS 2.0, and J-DOCSIS 2.0 in modular Integrated Service Routers as well as IAD2430 series routers

ciscoBr1430  OBJECT IDENTIFIER
    ::= { ciscoProducts 1030 }

-- Cisco 1400 series wireless LAN bridge

ciscoAIRBR1430  OBJECT IDENTIFIER
    ::= { ciscoProducts 1031 }

-- Cisco 1430 Series Wireless LAN Bridge with 4 GigabitEthernet Ports and one  4.9GHz  802.11A  or  5.8GHz 802.11N radio

ciscoNamApp2204  OBJECT IDENTIFIER
    ::= { ciscoProducts 1032 }

-- Cisco NAM Appliance 2204

ciscoNamApp2220  OBJECT IDENTIFIER
    ::= { ciscoProducts 1033 }

-- Cisco NAM Appliance 2220

ciscoAIRAP1141  OBJECT IDENTIFIER
    ::= { ciscoProducts 1034 }

-- Cisco Aironet 1140 series WLAN Access Point with one 10/100/1000TX port and single IEEE 802.11n radio port

ciscoAIRAP1142  OBJECT IDENTIFIER
    ::= { ciscoProducts 1035 }

-- Cisco Aironet 1140 series WLAN Access Point with one 10/100/1000TX port and dual IEEE 802.11n radio ports

ciscoASR14K4S  OBJECT IDENTIFIER
    ::= { ciscoProducts 1036 }

-- Cisco ASR14000 Series 4-Slot System

ciscoASR14K8S  OBJECT IDENTIFIER
    ::= { ciscoProducts 1037 }

-- Cisco ASR14000 Series 8-Slot System

cisco18xxx  OBJECT IDENTIFIER
    ::= { ciscoProducts 1038 }


ciscoIPSSSC5  OBJECT IDENTIFIER
    ::= { ciscoProducts 1039 }

-- Cisco Intrusion Prevention System Security Service Card SSC-5

cisco887Vdsl2  OBJECT IDENTIFIER
    ::= { ciscoProducts 1040 }

-- c887Vdsl2 with 1 VDSL2 only over POTS, 4 switch ports, 1 USB 1.1 port, 1 Console/Aux port and 1 ISDN

cisco3945  OBJECT IDENTIFIER
    ::= { ciscoProducts 1041 }

-- CISCO3945/K9 with SPE150(3 GE, 4  EHWIC, 4 DSP, 4 SM, 256MB CF, 1GB DRAM, IPB)

cisco3925  OBJECT IDENTIFIER
    ::= { ciscoProducts 1042 }

-- CISCO3925/K9 with SPE100(3 GE,  4 EHWIC, 4 DSP, 2 SM, 256MB CF, 1GB DRAM, IPB)

cisco2951  OBJECT IDENTIFIER
    ::= { ciscoProducts 1043 }

-- CISCO2951/K9 with 3 GE, 4 EHWIC, 3 DSP, 2 SM, 256 MB CF, 512 MB DRAM, IPB

cisco2921  OBJECT IDENTIFIER
    ::= { ciscoProducts 1044 }

-- CISCO2921/K9 with 3 GE, 4 EHWIC, 3 DSP, 1 SM, 256 MB CF, 512 MB DRAM, IPB

cisco2911  OBJECT IDENTIFIER
    ::= { ciscoProducts 1045 }

-- CISCO2911/K9 with 3 GE, 4 EHWIC, 2 DSP, 1 SM , 256 MB CF, 512 MB DRAM, IPB

cisco2901  OBJECT IDENTIFIER
    ::= { ciscoProducts 1046 }

-- CISCO2901/K9 with 2 GE, 4 EHWIC, 2 DSP, 256 MB CF, 512 MBDRAM, IP BASE

cisco1941  OBJECT IDENTIFIER
    ::= { ciscoProducts 1047 }

-- CISCO1941/K9  with 2 GE, 2 EHWIC, 256 MB CF, 256 MB DRAM, IP BASE

ciscoSm2k15Es1GePoe  OBJECT IDENTIFIER
    ::= { ciscoProducts 1048 }

-- EtherSwitch Service Module Layer2 + PoE + 15 10/100 + 1 10/100/1000

ciscoSm3k15Es1GePoe  OBJECT IDENTIFIER
    ::= { ciscoProducts 1049 }

-- EtherSwitch Service Module Layer3 + PoE + 15 10/100 + 1 10/100/1000

ciscoSm3k16GePoe  OBJECT IDENTIFIER
    ::= { ciscoProducts 1050 }

-- EtherSwitch Service Module Layer3 + PoE + 16 10/100/1000

ciscoSm2k23Es1Ge  OBJECT IDENTIFIER
    ::= { ciscoProducts 1051 }

-- EtherSwitch Service Module Layer2 + no PoE + 23 10/100 + 1 10/100/1000

ciscoSm2k23Es1GePoe  OBJECT IDENTIFIER
    ::= { ciscoProducts 1052 }

-- EtherSwitch Service Module Layer2 + PoE + 23 10/100 + 1 10/100/1000

ciscoSm3k23Es1GePoe  OBJECT IDENTIFIER
    ::= { ciscoProducts 1053 }

-- EtherSwitch Service Module Layer3 + PoE + 23 10/100 + 1 10/100/1000

ciscoSm3k24GePoe  OBJECT IDENTIFIER
    ::= { ciscoProducts 1054 }

-- EtherSwitch Service Module Layer3 + PoE + 24 10/100/1000

ciscoSmXd2k48Es2SFP  OBJECT IDENTIFIER
    ::= { ciscoProducts 1055 }

-- EtherSwitch Service Module Layer2 + no PoE + 48 10/100 + 2 SFP

ciscoSmXd3k48Es2SFPPoe  OBJECT IDENTIFIER
    ::= { ciscoProducts 1056 }

-- EtherSwitch Service Module Layer3 + PoE + 48 10/100 + 2 SFP

ciscoSmXd3k48Ge2SFPPoe  OBJECT IDENTIFIER
    ::= { ciscoProducts 1057 }

-- EtherSwitch Service ModuleLayer3 + PoE + 48 10/100/1000 + 2 SFP

ciscoEsw52024pK9  OBJECT IDENTIFIER
    ::= { ciscoProducts 1058 }

-- 24-port 10/100 Ethernet Switch with PoE

ciscoEsw54024pK9  OBJECT IDENTIFIER
    ::= { ciscoProducts 1059 }

-- 24-port 10/100/1000 Ethernet Switch with PoE

ciscoEsw52048pK9  OBJECT IDENTIFIER
    ::= { ciscoProducts 1060 }

-- 48-port 10/100 Ethernet Switch with PoE

ciscoEsw52024K9  OBJECT IDENTIFIER
    ::= { ciscoProducts 1061 }

-- 24-port 10/100 Ethernet Switch

ciscoEsw54024K9  OBJECT IDENTIFIER
    ::= { ciscoProducts 1062 }

-- 24-port 10/100/1000 Ethernet

ciscoEsw52048K9  OBJECT IDENTIFIER
    ::= { ciscoProducts 1063 }

-- 48-port 10/100 Ethernet Switch

ciscoEsw54048K9  OBJECT IDENTIFIER
    ::= { ciscoProducts 1064 }

-- 48-port 10/100/1000 Ethernet Switch

cisco1861  OBJECT IDENTIFIER
    ::= { ciscoProducts 1065 }

-- Cisco C1861 Base System

ciscoUC520  OBJECT IDENTIFIER
    ::= { ciscoProducts 1066 }

-- UC520 Base System

catalystWSC2975GS48PSL  OBJECT IDENTIFIER
    ::= { ciscoProducts 1067 }


catalystC2975Stack  OBJECT IDENTIFIER
    ::= { ciscoProducts 1068 }


cisco5500Wlc  OBJECT IDENTIFIER
    ::= { ciscoProducts 1069 }

-- Cisco 5500 series Wireless LAN Controller

ciscoSR520T1  OBJECT IDENTIFIER
    ::= { ciscoProducts 1070 }

-- Security router with 2 FE and 1 T1 port. Supports voice and data

ciscoPwrC3900Poe  OBJECT IDENTIFIER
    ::= { ciscoProducts 1071 }

-- Cisco 3925/3945 AC Power Supply with Power Over Ethernet (PWR-3900-POE)

ciscoPwrC3900AC  OBJECT IDENTIFIER
    ::= { ciscoProducts 1072 }

-- Cisco 3925/3945 AC Power Supply (PWR-3900-AC)

ciscoPwrC2921C2951Poe  OBJECT IDENTIFIER
    ::= { ciscoProducts 1073 }

-- Cisco 2921/2951 AC Power Supply with Power Over Ethernet (PWR-2921-51-POE)

ciscoPwrC2921C2951AC  OBJECT IDENTIFIER
    ::= { ciscoProducts 1074 }

-- Cisco 2921/2951 AC Power Supply (PWR-2921-51-AC)

ciscoPwrC2911Poe  OBJECT IDENTIFIER
    ::= { ciscoProducts 1075 }

-- Cisco 2911 AC Power Supply with Power Over Ethernet (PWR-2911-POE)

ciscoPwrC2911AC  OBJECT IDENTIFIER
    ::= { ciscoProducts 1076 }

-- Cisco 2911 AC Power Supply (PWR-2911-AC)

ciscoPwrC2901Poe  OBJECT IDENTIFIER
    ::= { ciscoProducts 1077 }

-- Cisco 2901 AC Power Supply with Power Over Ethernet(PWR-2901-POE)

ciscoPwrC1941C2901AC  OBJECT IDENTIFIER
    ::= { ciscoProducts 1078 }

-- Cisco 2901 AC Power Supply (PWR-2901-AC)

ciscoPwrC1941Poe  OBJECT IDENTIFIER
    ::= { ciscoProducts 1079 }

-- Cisco 1941 AC Power Supply with Power Over Ethernet (PWR-1941-POE)

ciscoPwrC3900DC  OBJECT IDENTIFIER
    ::= { ciscoProducts 1080 }

-- Cisco 3925/3945 DC Power Supply (PWR-3900-DC)

ciscoPwrC2921C2951DC  OBJECT IDENTIFIER
    ::= { ciscoProducts 1081 }

-- Cisco 2921/2951 DC Power Supply (PWR-2921-51-DC)

ciscoPwrC2911DC  OBJECT IDENTIFIER
    ::= { ciscoProducts 1082 }

-- Cisco 2911 DC power Supply (PWR-2911-DC)

ciscoRpsAdptrC2921C2951  OBJECT IDENTIFIER
    ::= { ciscoProducts 1083 }

-- Cisco 2921/2951 RPS Adaptor for use with external rps(RPS-ADPTR-2921-51)

ciscoRpsAdptrC2911  OBJECT IDENTIFIER
    ::= { ciscoProducts 1084 }

-- Cisco 2911 RPS Adaptor for use with external rps (RPS-ADPTR-2911)

ciscoIPSSSC2  OBJECT IDENTIFIER
    ::= { ciscoProducts 1085 }


ciscoIPSSSC2Virtual  OBJECT IDENTIFIER
    ::= { ciscoProducts 1086 }


catalystWSCBS3140XS  OBJECT IDENTIFIER
    ::= { ciscoProducts 1087 }


catalystWSCBS3140GS  OBJECT IDENTIFIER
    ::= { ciscoProducts 1088 }


catalystWSCBS3042FSC  OBJECT IDENTIFIER
    ::= { ciscoProducts 1089 }


catalystWSCBS3150XS  OBJECT IDENTIFIER
    ::= { ciscoProducts 1090 }


catalystWSCBS3150GS  OBJECT IDENTIFIER
    ::= { ciscoProducts 1091 }


catalystWSCBS3052NEC  OBJECT IDENTIFIER
    ::= { ciscoProducts 1092 }


ciscoCBS3140Stack  OBJECT IDENTIFIER
    ::= { ciscoProducts 1093 }

-- A stack of any CBS3140 switch modules.

ciscoCBS3150Stack  OBJECT IDENTIFIER
    ::= { ciscoProducts 1094 }

-- A stack of any CBS3150 switch modules.

cisco1941W  OBJECT IDENTIFIER
    ::= { ciscoProducts 1095 }

-- CISCO1941W-A/K9 with 802.11 a/b/g/ n  FCC compliant WLAN ISM

ciscoC888E  OBJECT IDENTIFIER
    ::= { ciscoProducts 1096 }


ciscoC888EG  OBJECT IDENTIFIER
    ::= { ciscoProducts 1097 }


ciscoIad888EB  OBJECT IDENTIFIER
    ::= { ciscoProducts 1098 }


ciscoIad888EF  OBJECT IDENTIFIER
    ::= { ciscoProducts 1099 }


ciscoC888ESRST  OBJECT IDENTIFIER
    ::= { ciscoProducts 1100 }


ciscoASA5505W  OBJECT IDENTIFIER
    ::= { ciscoProducts 1101 }


cisco3845nv  OBJECT IDENTIFIER
    ::= { ciscoProducts 1102 }

-- Four Network Module Slots, Four WIC slots, Two Gigabit Ethernet ports 3800nv family router

cisco3825nv  OBJECT IDENTIFIER
    ::= { ciscoProducts 1103 }

-- Two Network Module Slots, Four WIC slots, Two Gigabit Ethernet ports 3800nv family router

catalystWSC235048TD  OBJECT IDENTIFIER
    ::= { ciscoProducts 1104 }

-- Catalyst 2350 48 10/100/1000 ports + 2 TenGigabit Ethernet (X2) ports fixed configuration Layer 2 Ethernet Switch

cisco887M  OBJECT IDENTIFIER
    ::= { ciscoProducts 1105 }

-- c887 with 1 ADSL2/2+ AnnexM,4 switch ports, 1 USB 1.1 port, 1 Console/Aux port, 1 ISDN, and an optional Wireless LAN

ciscoVg250  OBJECT IDENTIFIER
    ::= { ciscoProducts 1106 }


ciscoVg226e  OBJECT IDENTIFIER
    ::= { ciscoProducts 1107 }


ciscoDsIbm8GfcK9  OBJECT IDENTIFIER
    ::= { ciscoProducts 1108 }


ciscoDsHp8GfcK9  OBJECT IDENTIFIER
    ::= { ciscoProducts 1109 }


ciscoDsDell8GfcK9  OBJECT IDENTIFIER
    ::= { ciscoProducts 1110 }


ciscoDsC9148K9  OBJECT IDENTIFIER
    ::= { ciscoProducts 1111 }


ciscoCeVirtualBlade  OBJECT IDENTIFIER
    ::= { ciscoProducts 1112 }

-- Cisco Content Engine

ciscoCDScde420  OBJECT IDENTIFIER
    ::= { ciscoProducts 1113 }

-- Cisco Content Delivery System Model CDE-420

ciscoCDScde220  OBJECT IDENTIFIER
    ::= { ciscoProducts 1114 }

-- Cisco Content Delivery System Model CDE-220

ciscoCDScde110  OBJECT IDENTIFIER
    ::= { ciscoProducts 1115 }

-- Cisco Content Delivery System Model CDE-110

ciscoASR1002F  OBJECT IDENTIFIER
    ::= { ciscoProducts 1116 }

-- Cisco Aggregation Services Router 1000 Series with 2RU Fixed Chassis

ciscoSecureAccessControlSystem  OBJECT IDENTIFIER
    ::= { ciscoProducts 1117 }

-- Cisco Secure Access Control System

cisco861Npe  OBJECT IDENTIFIER
    ::= { ciscoProducts 1118 }


cisco881Npe  OBJECT IDENTIFIER
    ::= { ciscoProducts 1119 }


cisco881GNpe  OBJECT IDENTIFIER
    ::= { ciscoProducts 1120 }


cisco887Npe  OBJECT IDENTIFIER
    ::= { ciscoProducts 1121 }


cisco888GNpe  OBJECT IDENTIFIER
    ::= { ciscoProducts 1122 }


cisco891Npe  OBJECT IDENTIFIER
    ::= { ciscoProducts 1123 }


ciscoAIRAP3501  OBJECT IDENTIFIER
    ::= { ciscoProducts 1124 }


ciscoAIRAP3502  OBJECT IDENTIFIER
    ::= { ciscoProducts 1125 }


ciscoCDScde400  OBJECT IDENTIFIER
    ::= { ciscoProducts 1126 }

-- Cisco Content Delivery System Model CDE-400

ciscoSA520K9  OBJECT IDENTIFIER
    ::= { ciscoProducts 1127 }


ciscoSA520WK9  OBJECT IDENTIFIER
    ::= { ciscoProducts 1128 }


ciscoSA540K9  OBJECT IDENTIFIER
    ::= { ciscoProducts 1129 }


ciscoSps2004B  OBJECT IDENTIFIER
    ::= { ciscoProducts 1130 }

-- Metro Ethernet Switch with 1 1000Base-BX-U WAN port and 5 10/100/1000M LAN ports

ciscoSps204B  OBJECT IDENTIFIER
    ::= { ciscoProducts 1131 }

-- Metro Ethernet Switch with 1 100Base-BX-U WAN and 5 10/100/1000M LAN ports

ciscoUC560T1E1K9  OBJECT IDENTIFIER
    ::= { ciscoProducts 1132 }


ciscoUC560BRIK9  OBJECT IDENTIFIER
    ::= { ciscoProducts 1133 }


ciscoUC560FXOK9  OBJECT IDENTIFIER
    ::= { ciscoProducts 1134 }


ciscoAp541nAK9  OBJECT IDENTIFIER
    ::= { ciscoProducts 1135 }

-- 802.11a/b/g/n Wireless LAN Access Point for North America, FCC band plan

ciscoAp541nEK9  OBJECT IDENTIFIER
    ::= { ciscoProducts 1136 }

-- 802.11a/b/g/n Wireless LAN Access Point for Europe, ETSI band plan

ciscoAp541nNK9  OBJECT IDENTIFIER
    ::= { ciscoProducts 1137 }

-- 802.11a/b/g/n Wireless LAN Access Point for ANZ band plan

cisco887GVdsl2  OBJECT IDENTIFIER
    ::= { ciscoProducts 1138 }

-- c887GVdsl2 with 1 VDSL2 only over POTS,4 switch ports, 1 USB 2.0 port, 1 Console/Aux port, 1 3G PCMCIA slot, and an optional Wireless LAN

cisco887SrstVdsl2  OBJECT IDENTIFIER
    ::= { ciscoProducts 1139 }

-- c887SRSTVdsl2 with 1 VDSL2 over POTS, 4 switch ports, 1 USB 1.1 port, 1 Console/Aux port, 4 FXS ports, 1 PSTN BRI port, and an optional Wireless LAN

ciscoUc540wFxoK9  OBJECT IDENTIFIER
    ::= { ciscoProducts 1140 }


ciscoUc540wBriK9  OBJECT IDENTIFIER
    ::= { ciscoProducts 1141 }


ciscoCaServer  OBJECT IDENTIFIER
    ::= { ciscoProducts 1142 }


ciscoCaManager  OBJECT IDENTIFIER
    ::= { ciscoProducts 1143 }


cisco3925SPE200  OBJECT IDENTIFIER
    ::= { ciscoProducts 1144 }

-- Cisco 3925 w/SPE200(4 GE, 3 EHWIC, 3 DSP,  2 SM)

cisco3945SPE250  OBJECT IDENTIFIER
    ::= { ciscoProducts 1145 }

-- Cisco 3945 w/SPE250(4 GE, 3 EHWIC, 3 DSP, 4 SM)

catalyst296024LCS  OBJECT IDENTIFIER
    ::= { ciscoProducts 1146 }

-- Catalyst 2960 8 10/100 Power over Ethernet ports + 16 10/100 Ethernet ports + 2 dual purpose Gigabit Ethernet ports fixed configuration Layer 2 Ethernet switch

catalyst296024PCS  OBJECT IDENTIFIER
    ::= { ciscoProducts 1147 }

-- Catalyst 2960 24 10/100 Power over Ethernet ports + 2 dual purpose Gigabit Ethernet ports fixed configuration Layer 2 Ethernet switch

catalyst296048PSTS  OBJECT IDENTIFIER
    ::= { ciscoProducts 1148 }

-- Catalyst 2960 48 10/100 Power over Ethernet ports + 2 10/100/1000 Ethernet ports + 2 SFP fixed configuration Layer 2 Ethernet switch

ciscoISM  OBJECT IDENTIFIER
    ::= { ciscoProducts 1149 }


ciscoSM  OBJECT IDENTIFIER
    ::= { ciscoProducts 1150 }


ciscoNMEAXP  OBJECT IDENTIFIER
    ::= { ciscoProducts 1151 }

-- Cisco Application Extension Platform Network Module Enhanced (NME-AXP)

ciscoAIMAXP  OBJECT IDENTIFIER
    ::= { ciscoProducts 1152 }

-- Cisco Application Extension Platform advanced integration module (AIM-AXP)

ciscoAIM2AXP  OBJECT IDENTIFIER
    ::= { ciscoProducts 1153 }

-- Cisco Application Extension Platform advanced integration module 2(AIM2-AXP)

ciscoSRP521  OBJECT IDENTIFIER
    ::= { ciscoProducts 1154 }

-- Service Ready Platform router with Fast Ethernet WAN port

ciscoSRP526  OBJECT IDENTIFIER
    ::= { ciscoProducts 1155 }

-- Service Ready Platform router with ADSL2+ over ISDN WAN port

ciscoSRP527  OBJECT IDENTIFIER
    ::= { ciscoProducts 1156 }

-- Service Ready Platform router with ADSL2+ over POTS WAN port

ciscoSRP541  OBJECT IDENTIFIER
    ::= { ciscoProducts 1157 }

-- Service Ready Platform router with GE WAN port

ciscoSRP546  OBJECT IDENTIFIER
    ::= { ciscoProducts 1158 }

-- Service Ready Platform router with ADSL2+ over ISDN WAN port as well as GE WAN port

ciscoSRP547  OBJECT IDENTIFIER
    ::= { ciscoProducts 1159 }

-- Service Ready Platform router with ADSL2+ over POTS WAN port as well as GE WAN port

ciscoVS510FXO  OBJECT IDENTIFIER
    ::= { ciscoProducts 1160 }

-- Call control solution for 4-24 phone

ciscoNmWae900  OBJECT IDENTIFIER
    ::= { ciscoProducts 1161 }

-- Cisco Network Module Intergrated Service Engine 900

ciscoNmWae700  OBJECT IDENTIFIER
    ::= { ciscoProducts 1162 }

-- Cisco Network Module Intergrated Service Engine 700

cisco5940RA  OBJECT IDENTIFIER
    ::= { ciscoProducts 1163 }


cisco5940RC  OBJECT IDENTIFIER
    ::= { ciscoProducts 1164 }


ciscoASR1001  OBJECT IDENTIFIER
    ::= { ciscoProducts 1165 }


ciscoASR1013  OBJECT IDENTIFIER
    ::= { ciscoProducts 1166 }


ciscoCDScde205  OBJECT IDENTIFIER
    ::= { ciscoProducts 1167 }

-- Cisco Content Delivery System Model CDE-205

ciscoPwr1941AC  OBJECT IDENTIFIER
    ::= { ciscoProducts 1168 }

-- C1941 AC Power Supply

ciscoNamWaasVirtualBlade  OBJECT IDENTIFIER
    ::= { ciscoProducts 1169 }

-- Cisco Network Analysis Module (NAM) Virtual Blade on WAAS appliance

ciscoRaie1783Rms06t  OBJECT IDENTIFIER
    ::= { ciscoProducts 1170 }

-- Cisco Rockwell brand Layer 3 Industrial Ethernet  Switch, 4 10/100 + 2 T/SFP

ciscoRaie1783Rms10t  OBJECT IDENTIFIER
    ::= { ciscoProducts 1171 }

-- Cisco Rockwell brand Industrial Ethernet Switch, 8 10/100 + 2 T/SFP

cisco1941WEK9  OBJECT IDENTIFIER
    ::= { ciscoProducts 1172 }

-- CISCO1941W-E/K9 Router w/ 802.11 a/b/g/n ETSI Compliant WLAN ISM

cisco1941WPK9  OBJECT IDENTIFIER
    ::= { ciscoProducts 1173 }

-- CISCO1941W-P/K9 Router w/ 802.11 a/b/g/n Japan Compliant WLAN ISM

cisco1941WNK9  OBJECT IDENTIFIER
    ::= { ciscoProducts 1174 }

-- CISCO1941W-N/K9 Router w/ 802.11 a/b/g/n Aus, NZ Compliant WLAN ISM

ciscoMXE5600  OBJECT IDENTIFIER
    ::= { ciscoProducts 1175 }

-- Cisco MXE 5600 platform, 1 Rack Unit (RU) application specific device with 8 slots

ciscoEsw5408pK9  OBJECT IDENTIFIER
    ::= { ciscoProducts 1176 }

-- Cisco ESW 540 8-port 10/100/1000 PoE switch

ciscoEsw5208pK9  OBJECT IDENTIFIER
    ::= { ciscoProducts 1177 }

-- Cisco ESW 520 8-port 10/100 PoW switch

catalyst4948e10GE  OBJECT IDENTIFIER
    ::= { ciscoProducts 1178 }

-- Catalyst 4000 series fixed configuration switch with 48 10/100/1000BaseT ports and four 10Gbps/1Gbps SFP+/SFP ports(WS-C4948E)

cat2960x48tsS  OBJECT IDENTIFIER
    ::= { ciscoProducts 1179 }


cat2960x24tsS  OBJECT IDENTIFIER
    ::= { ciscoProducts 1180 }


cat2960xs48fpdL  OBJECT IDENTIFIER
    ::= { ciscoProducts 1181 }


cat2960xs48lpdL  OBJECT IDENTIFIER
    ::= { ciscoProducts 1182 }


cat2960xs48ltdL  OBJECT IDENTIFIER
    ::= { ciscoProducts 1183 }


cat2960xs24pdL  OBJECT IDENTIFIER
    ::= { ciscoProducts 1184 }


cat2960xs24tdL  OBJECT IDENTIFIER
    ::= { ciscoProducts 1185 }


cat2960xs48fpsL  OBJECT IDENTIFIER
    ::= { ciscoProducts 1186 }


cat2960xs48lpsL  OBJECT IDENTIFIER
    ::= { ciscoProducts 1187 }


cat2960xs24psL  OBJECT IDENTIFIER
    ::= { ciscoProducts 1188 }


cat2960xs48tsL  OBJECT IDENTIFIER
    ::= { ciscoProducts 1189 }


cat2960xs24tsL  OBJECT IDENTIFIER
    ::= { ciscoProducts 1190 }


cisco1921k9  OBJECT IDENTIFIER
    ::= { ciscoProducts 1191 }

-- CISCO1921/K9 with 2 GE, 2 EHWIC, 256 MB flash memory, 512 MB DRAM, IP BASE

cisco1905k9  OBJECT IDENTIFIER
    ::= { ciscoProducts 1192 }


ciscoPwrC1921C1905AC  OBJECT IDENTIFIER
    ::= { ciscoProducts 1193 }


ciscoASA5585Ssp10  OBJECT IDENTIFIER
    ::= { ciscoProducts 1194 }


ciscoASA5585Ssp20  OBJECT IDENTIFIER
    ::= { ciscoProducts 1195 }


ciscoASA5585Ssp40  OBJECT IDENTIFIER
    ::= { ciscoProducts 1196 }


ciscoASA5585Ssp60  OBJECT IDENTIFIER
    ::= { ciscoProducts 1197 }


ciscoASA5585Ssp10sc  OBJECT IDENTIFIER
    ::= { ciscoProducts 1198 }


ciscoASA5585Ssp20sc  OBJECT IDENTIFIER
    ::= { ciscoProducts 1199 }


ciscoASA5585Ssp40sc  OBJECT IDENTIFIER
    ::= { ciscoProducts 1200 }


ciscoASA5585Ssp60sc  OBJECT IDENTIFIER
    ::= { ciscoProducts 1201 }


ciscoASA5585Ssp10sy  OBJECT IDENTIFIER
    ::= { ciscoProducts 1202 }


ciscoASA5585Ssp20sy  OBJECT IDENTIFIER
    ::= { ciscoProducts 1203 }


ciscoASA5585Ssp40sy  OBJECT IDENTIFIER
    ::= { ciscoProducts 1204 }


ciscoASA5585Ssp60sy  OBJECT IDENTIFIER
    ::= { ciscoProducts 1205 }


cisco3925SPE250  OBJECT IDENTIFIER
    ::= { ciscoProducts 1206 }


cisco3945SPE200  OBJECT IDENTIFIER
    ::= { ciscoProducts 1207 }


cat29xxStack  OBJECT IDENTIFIER
    ::= { ciscoProducts 1208 }


ciscoOeNm302  OBJECT IDENTIFIER
    ::= { ciscoProducts 1209 }


ciscoOeNm502  OBJECT IDENTIFIER
    ::= { ciscoProducts 1210 }


ciscoOeNm522  OBJECT IDENTIFIER
    ::= { ciscoProducts 1211 }


ciscoOeSmSre700  OBJECT IDENTIFIER
    ::= { ciscoProducts 1212 }


ciscoOeSmSre900  OBJECT IDENTIFIER
    ::= { ciscoProducts 1213 }


ciscoVsaNam  OBJECT IDENTIFIER
    ::= { ciscoProducts 1214 }

-- Virtual Switch NAM for Nexus1010

ciscoMwr2941DCA  OBJECT IDENTIFIER
    ::= { ciscoProducts 1215 }

-- The Mobile Wireless router MWR-2941-DC-A is a router targeted at application in a cell site Base Transciever Station (BTS) providing Radio Access Network (RAN) optimization

ciscoN7KC7018IOS  OBJECT IDENTIFIER
    ::= { ciscoProducts 1216 }


ciscoN7KC7010IOS  OBJECT IDENTIFIER
    ::= { ciscoProducts 1217 }


ciscoN4KDellEth  OBJECT IDENTIFIER
    ::= { ciscoProducts 1218 }


ciscoN4KDellCiscoEth  OBJECT IDENTIFIER
    ::= { ciscoProducts 1219 }


cisco1941WCK9  OBJECT IDENTIFIER
    ::= { ciscoProducts 1220 }

-- CISCO1941W-C/K9 Router w/ 802.11 a/b/g/n China Compliant WLAN ISM

ciscoCDScde2202s3  OBJECT IDENTIFIER
    ::= { ciscoProducts 1221 }

-- Cisco Content Delivery System Model CDE-220-2S3

cat3750x24  OBJECT IDENTIFIER
    ::= { ciscoProducts 1222 }

-- Catalyst 3750X 24 10/100/1000 Ports + 4 SFP Ports + 2 SFP+ Ports Layer 2/Layer 3 Ethernet Stackable Switch

cat3750x48  OBJECT IDENTIFIER
    ::= { ciscoProducts 1223 }

-- Catalyst 3750X 48 10/100/1000 Ports + 4 SFP Ports + 2 SFP+ Ports Layer 2/Layer 3 Ethernet Stackable Switch

cat3750x24P  OBJECT IDENTIFIER
    ::= { ciscoProducts 1224 }

-- Catalyst 3750X 24 10/100/1000 PoE Ports + 4 SFP Ports + 2 SFP+ Ports Layer 2/Layer 3 Ethernet Stackable Switch

cat3750x48P  OBJECT IDENTIFIER
    ::= { ciscoProducts 1225 }

-- Catalyst 3750X 48 10/100/1000 PoE Ports + 4 SFP Ports + 2 SFP+ Ports Layer 2/Layer 3 Ethernet Stackable Switch

cat3560x24  OBJECT IDENTIFIER
    ::= { ciscoProducts 1226 }

-- Catalyst 3560X 24 10/100/1000 Ports + 4 SFP Ports + 2 SFP+ Ports Layer 2/Layer 3 Ethernet Switch

cat3560x48  OBJECT IDENTIFIER
    ::= { ciscoProducts 1227 }

-- Catalyst 3560X 48 10/100/1000 Ports + 4 SFP Ports + 2 SFP+ Ports Layer 2/Layer 3 Ethernet Switch

cat3560x24P  OBJECT IDENTIFIER
    ::= { ciscoProducts 1228 }

-- Catalyst 3560X 24 10/100/1000 PoE Ports + 4 SFP Ports + 2 SFP+ Ports Layer 2/Layer 3 Ethernet Switch

cat3560x48P  OBJECT IDENTIFIER
    ::= { ciscoProducts 1229 }

-- Catalyst 3560X 48 10/100/1000 PoE Ports + 4 SFP Ports + 2 SFP+ Ports Layer 2/Layer 3 Ethernet Switch

ciscoNMEAIR  OBJECT IDENTIFIER
    ::= { ciscoProducts 1230 }


ciscoACE30K9  OBJECT IDENTIFIER
    ::= { ciscoProducts 1231 }

-- Application Control Engine Module in Cat6500

ciscoASA5585SspIps10  OBJECT IDENTIFIER
    ::= { ciscoProducts 1232 }

-- Cisco Adaptive Security Appliance 5585-X IPS Security Services Processor-10

ciscoASA5585SspIps20  OBJECT IDENTIFIER
    ::= { ciscoProducts 1233 }

-- Cisco Adaptive Security Appliance 5585-X IPS Security Services Processor-20

ciscoASA5585SspIps40  OBJECT IDENTIFIER
    ::= { ciscoProducts 1234 }

-- Cisco Adaptive Security Appliance 5585-X IPS Security Services Processor-40

ciscoASA5585SspIps60  OBJECT IDENTIFIER
    ::= { ciscoProducts 1235 }

-- Cisco Adaptive Security Appliance 5585-X IPS Security Services Processor-60

cisco1841CK9  OBJECT IDENTIFIER
    ::= { ciscoProducts 1236 }

-- Cisco 1841C/K9 data only router with 2 HWIC slots

cisco2801CK9  OBJECT IDENTIFIER
    ::= { ciscoProducts 1237 }

-- Cisco 2801C/K9 router with 4 HWIC slots

cisco2811CK9  OBJECT IDENTIFIER
    ::= { ciscoProducts 1238 }

-- Cisco 2811C/K9 router with one Network Module slot, four HWIC slots, two fast ethernet and integrated VPN

cisco2821CK9  OBJECT IDENTIFIER
    ::= { ciscoProducts 1239 }

-- Cisco 2821C/K9 router with one Network Module slot, one EVM, four HWIC slots, two gigabit ethernet and intergrated VPN

cisco2851CK9  OBJECT IDENTIFIER
    ::= { ciscoProducts 1240 }


cisco3825CK9  OBJECT IDENTIFIER
    ::= { ciscoProducts 1241 }

-- Cisco 3825C/K9 router with Two Network Module Slots, Four WIC slots, Two Gigabit Ethernet ports

cisco3845CK9  OBJECT IDENTIFIER
    ::= { ciscoProducts 1242 }

-- Cisco 3845C/K9 router with Four Network Module Slots, Four WIC slots, Two Gigabit Ethernet ports

cisco3825CnvK9  OBJECT IDENTIFIER
    ::= { ciscoProducts 1243 }


cisco3845CnvK9  OBJECT IDENTIFIER
    ::= { ciscoProducts 1244 }


ciscoCGS252024TC  OBJECT IDENTIFIER
    ::= { ciscoProducts 1245 }


ciscoCGS252016S8PC  OBJECT IDENTIFIER
    ::= { ciscoProducts 1246 }


ciscoAIRAP1262  OBJECT IDENTIFIER
    ::= { ciscoProducts 1247 }


ciscoAIRAP1261  OBJECT IDENTIFIER
    ::= { ciscoProducts 1248 }


cisco892F  OBJECT IDENTIFIER
    ::= { ciscoProducts 1249 }


ciscoMe3600x24fsM  OBJECT IDENTIFIER
    ::= { ciscoProducts 1250 }


ciscoMe3600x24tsM  OBJECT IDENTIFIER
    ::= { ciscoProducts 1251 }


ciscoMe3800x24fsM  OBJECT IDENTIFIER
    ::= { ciscoProducts 1252 }


ciscoCGR2010  OBJECT IDENTIFIER
    ::= { ciscoProducts 1253 }


ciscoPwrCGR20xxCGS25xxPoeAC  OBJECT IDENTIFIER
    ::= { ciscoProducts 1254 }


ciscoPwrCGR20xxCGS25xxPoeDC  OBJECT IDENTIFIER
    ::= { ciscoProducts 1255 }


catWsC2960s48tsS  OBJECT IDENTIFIER
    ::= { ciscoProducts 1256 }

-- Catalyst 2960S 48 Gig Downlinks and 2 SFP uplink, Non-stackable module

catWsC2960s24tsS  OBJECT IDENTIFIER
    ::= { ciscoProducts 1257 }

-- Catalyst 2960S 24 Gig Downlinks and 2 SFP uplink, Non-stackable module

catWsC2960s48fpdL  OBJECT IDENTIFIER
    ::= { ciscoProducts 1258 }

-- Catalyst 2960S 48 Gig Downlinks and 4 SFP uplink with support for a 2 x 10G stacking module. POE support for 740W

catWsC2960s48ldpL  OBJECT IDENTIFIER
    ::= { ciscoProducts 1259 }

-- Catalyst 2960S 48 Gig Downlinks and 2 SFP+ uplink with support for a 2 x 10G stacking module. POE support for 370W

catWsC2960s48tdL  OBJECT IDENTIFIER
    ::= { ciscoProducts 1260 }

-- Catalyst 2960S 48 Gig Downlinks and 2 SFP+ uplink with support for a 2 x 10G stacking module

catWsC2960s24pdL  OBJECT IDENTIFIER
    ::= { ciscoProducts 1261 }

-- Catalyst 2960S 24 Gig Downlinks and 2 SFP+ uplink with support for a 2 x 10G stacking module. POE support for 370W

catWsC2960s24tdL  OBJECT IDENTIFIER
    ::= { ciscoProducts 1262 }

-- Catalyst 2960S 24 Gig Downlinks and 2 SFP+ uplink with support for a 2 x 10G stacking module

catWsC2960s48fpsL  OBJECT IDENTIFIER
    ::= { ciscoProducts 1263 }

-- Catalyst 2960S 48 Gig Downlinks and 4 SFP uplink with support for a 2 x 10G stacking module. POE support for 740W

catWsC2960s48lpsL  OBJECT IDENTIFIER
    ::= { ciscoProducts 1264 }

-- Catalyst 2960S 48 Gig Downlinks and 4 SFP uplink with support for a 2 x 10G stacking module. POE support for 370W

catWsC2960s24psL  OBJECT IDENTIFIER
    ::= { ciscoProducts 1265 }

-- Catalyst 2960S 24 Gig Downlinks and 4 SFP uplink with support for a 2 x 10G stacking module. POE support for 370W

catWsC2960s48tsL  OBJECT IDENTIFIER
    ::= { ciscoProducts 1266 }

-- Catalyst 2960S 48 Gig Downlinks and 4 SFP uplink with support for a 2 x 10G stacking module

catWsC2960s24tsL  OBJECT IDENTIFIER
    ::= { ciscoProducts 1267 }

-- Catalyst 2960S 24 Gig Downlinks and 4 SFP uplink with support for a 2 x 10G stacking module

cisco1906CK9  OBJECT IDENTIFIER
    ::= { ciscoProducts 1268 }

-- Cisco 1906C/K9 router  with 2 GE, Serial 1T, 1 EHWIC, 256 MB flash memory, 512 MB DRAM

ciscoAIRAP1042  OBJECT IDENTIFIER
    ::= { ciscoProducts 1269 }


ciscoAIRAP1041  OBJECT IDENTIFIER
    ::= { ciscoProducts 1270 }


cisco887VaM  OBJECT IDENTIFIER
    ::= { ciscoProducts 1271 }


cisco867Va  OBJECT IDENTIFIER
    ::= { ciscoProducts 1272 }


cisco886Va  OBJECT IDENTIFIER
    ::= { ciscoProducts 1273 }


cisco887Va  OBJECT IDENTIFIER
    ::= { ciscoProducts 1274 }


ciscoASASm1sc  OBJECT IDENTIFIER
    ::= { ciscoProducts 1275 }


ciscoASASm1sy  OBJECT IDENTIFIER
    ::= { ciscoProducts 1276 }


ciscoASASm1  OBJECT IDENTIFIER
    ::= { ciscoProducts 1277 }


cat2960cPD8TT  OBJECT IDENTIFIER
    ::= { ciscoProducts 1278 }


ciscoAirCt2504K9  OBJECT IDENTIFIER
    ::= { ciscoProducts 1279 }

-- Szabla: Cisco 2500 Series Wireless LAN Controller

ciscoISMAXP  OBJECT IDENTIFIER
    ::= { ciscoProducts 1280 }

-- Cisco Application Extension Platform Internal Service Module (ISM) with Services Ready Engine (SRE) for ISR routers

ciscoSMAXP  OBJECT IDENTIFIER
    ::= { ciscoProducts 1281 }

-- Cisco Application Extension Platform Service Module (SM) with Services Ready Engine (SRE) for ISR routers

ciscoAxpSmSre900  OBJECT IDENTIFIER
    ::= { ciscoProducts 1282 }

-- Cisco Application Extension Platform Service Module (SM) with Services Ready Engine (SM-SRE-900-K9) for ISR routers

ciscoAxpSmSre700  OBJECT IDENTIFIER
    ::= { ciscoProducts 1283 }

-- Cisco Application Extension Platform Service Module (SM) with Services Ready Engine (SM-SRE-700-K9) for ISR routers

ciscoAxpIsmSre300  OBJECT IDENTIFIER
    ::= { ciscoProducts 1284 }

-- Cisco Application Extension Platform Internal Service Module (ISM) with Services Ready Engine (ISM-SRE-300-K9) for ISR routers

ciscoCDSAVSM  OBJECT IDENTIFIER
    ::= { ciscoProducts 1285 }

-- Cisco Content Delivery System Model AVSM line card

cat4507rpluse  OBJECT IDENTIFIER
    ::= { ciscoProducts 1286 }


cat4510rpluse  OBJECT IDENTIFIER
    ::= { ciscoProducts 1287 }


ciscoAxpNme302  OBJECT IDENTIFIER
    ::= { ciscoProducts 1288 }

-- Cisco Application Extension Platform Network Module Enhanced (NME-APPRE-302-K9) for ISR routers

ciscoAxpNme502  OBJECT IDENTIFIER
    ::= { ciscoProducts 1289 }

-- Cisco Application Extension Platform Network Module Enhanced (NME-APPRE-502-K9) for ISR routers

ciscoAxpNme522  OBJECT IDENTIFIER
    ::= { ciscoProducts 1290 }

-- Cisco Application Extension Platform Network Module Enhanced (NME-APPRE-522-K9) for ISR routers

ciscoACE20K9  OBJECT IDENTIFIER
    ::= { ciscoProducts 1291 }

-- Application Control Engine Module in Cat6500

ciscoWsC236048tdS  OBJECT IDENTIFIER
    ::= { ciscoProducts 1292 }


ciscoWiSM2  OBJECT IDENTIFIER
    ::= { ciscoProducts 1293 }


ciscoCDScde250  OBJECT IDENTIFIER
    ::= { ciscoProducts 1294 }

-- Cisco Content Delivery System Model CDE-250

cisco7500Wlc  OBJECT IDENTIFIER
    ::= { ciscoProducts 1295 }


ciscoAnmVirtualApp  OBJECT IDENTIFIER
    ::= { ciscoProducts 1296 }

-- Cisco Application Networking Manager Virtual Appliance

ciscoECDS3100  OBJECT IDENTIFIER
    ::= { ciscoProducts 1297 }

-- Cisco Enterprise Content Delivery System Model ECDS-3100

ciscoECDS1100  OBJECT IDENTIFIER
    ::= { ciscoProducts 1298 }

-- Cisco Enterprise Content Delivery System Model ECDS-1100

cisco881G2  OBJECT IDENTIFIER
    ::= { ciscoProducts 1299 }


catWsC3750v224fsS  OBJECT IDENTIFIER
    ::= { ciscoProducts 1300 }


ciscoOeVWaas  OBJECT IDENTIFIER
    ::= { ciscoProducts 1301 }


ciscoASA5585Ssp10K7  OBJECT IDENTIFIER
    ::= { ciscoProducts 1302 }


ciscoASA5585Ssp20K7  OBJECT IDENTIFIER
    ::= { ciscoProducts 1303 }


ciscoASA5585Ssp40K7  OBJECT IDENTIFIER
    ::= { ciscoProducts 1304 }


ciscoASA5585Ssp60K7  OBJECT IDENTIFIER
    ::= { ciscoProducts 1305 }


ciscoASA5585Ssp10K7sc  OBJECT IDENTIFIER
    ::= { ciscoProducts 1306 }


ciscoASA5585Ssp20K7sc  OBJECT IDENTIFIER
    ::= { ciscoProducts 1307 }


ciscoASA5585Ssp40K7sc  OBJECT IDENTIFIER
    ::= { ciscoProducts 1308 }


ciscoASA5585Ssp60K7sc  OBJECT IDENTIFIER
    ::= { ciscoProducts 1309 }


ciscoASA5585Ssp10K7sy  OBJECT IDENTIFIER
    ::= { ciscoProducts 1310 }


ciscoASA5585Ssp20K7sy  OBJECT IDENTIFIER
    ::= { ciscoProducts 1311 }


ciscoASA5585Ssp40K7sy  OBJECT IDENTIFIER
    ::= { ciscoProducts 1312 }


ciscoASA5585Ssp60K7sy  OBJECT IDENTIFIER
    ::= { ciscoProducts 1313 }


ciscoSreSmNam  OBJECT IDENTIFIER
    ::= { ciscoProducts 1314 }

-- Cisco Network Analysis Module (NAM) on SM-SRE

cat2960cPD8PT  OBJECT IDENTIFIER
    ::= { ciscoProducts 1315 }


cat2960cG8TC  OBJECT IDENTIFIER
    ::= { ciscoProducts 1316 }


cat3560cG8PC  OBJECT IDENTIFIER
    ::= { ciscoProducts 1317 }


cat3560cG8TC  OBJECT IDENTIFIER
    ::= { ciscoProducts 1318 }


ciscoIE301016S8PC  OBJECT IDENTIFIER
    ::= { ciscoProducts 1319 }


ciscoIE301024TC  OBJECT IDENTIFIER
    ::= { ciscoProducts 1320 }


ciscoRAIE1783RMSB10T  OBJECT IDENTIFIER
    ::= { ciscoProducts 1321 }


ciscoRAIE1783RMSB06T  OBJECT IDENTIFIER
    ::= { ciscoProducts 1322 }


ciscoASA5585SspIps10K7  OBJECT IDENTIFIER
    ::= { ciscoProducts 1323 }


ciscoASA5585SspIps20K7  OBJECT IDENTIFIER
    ::= { ciscoProducts 1324 }


ciscoASA5585SspIps40K7  OBJECT IDENTIFIER
    ::= { ciscoProducts 1325 }


ciscoASA5585SspIps60K7  OBJECT IDENTIFIER
    ::= { ciscoProducts 1326 }


catalyst4948ef10GE  OBJECT IDENTIFIER
    ::= { ciscoProducts 1327 }


cat292824TCC  OBJECT IDENTIFIER
    ::= { ciscoProducts 1328 }


cat292848TCC  OBJECT IDENTIFIER
    ::= { ciscoProducts 1329 }


cat292824LTC  OBJECT IDENTIFIER
    ::= { ciscoProducts 1330 }


ciscoCrs16SB  OBJECT IDENTIFIER
    ::= { ciscoProducts 1331 }


ciscoQuad  OBJECT IDENTIFIER
    ::= { ciscoProducts 1332 }


ciscoPwrC2935PoeAC  OBJECT IDENTIFIER
    ::= { ciscoProducts 9998 }


ciscoPwrC2935PoeDC  OBJECT IDENTIFIER
    ::= { ciscoProducts 9999 }

END
